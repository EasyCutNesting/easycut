(defun c:AccessDatabaseADO ( / daoObj dbObj rstObj fieldsObj) ;; Load the ADO library (if (= adoLibImport nil) (progn (vlax-import-type-library :tlb-filename (strcat (ExpEnvStr "%PROGRAMFILES%") "\\Common Files\\System\\ado\\msado15.dll") :methods-prefix "adom-" :properties-prefix "adop-" :constants-prefix "adoc-" ) (setq adoLibImport T) ) ) ;; Create a recordset and connection object (setq adoRecordset (vlax-create-object "ADODB.Recordset")) (setq adoConnection (vlax-create-object "ADODB.Connection")) (setq strConnection (strcat "Provider=Microsoft.ACE.OLEDB.12.0;" "Data Source=c:\\datasets\\lee ambrosius\\sd196926\\AU2018.mdb;" "Jet OLEDB:Database Password=;")) ;; Open the database (adom-open adoConnection strConnection "" nil nil) ;; Open the table (adom-open adoRecordset "tblEmployees" adoConnection adoc-adOpenKeyset adoc-adLockOptimistic
