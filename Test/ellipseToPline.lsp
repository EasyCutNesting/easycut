(defun Ellipse2LwPolyline (Ename Flag / *error* ElliToPoly 
										acdoc Rtn)

	(defun *error* (msg)
		(princ msg)
		(vla-endUndoMark acdoc)
	)
	;
	(defun ElliToPoly (el / ang<2pi 3dTo2dPt tan sublist k*bulge 
								  cl norm cen elv pt0 pt1 pt2 pt3 pt4 ac0
								  ac4 a04 a02 a24 bsc0 bsc2 bsc3 bsc4 plst blst spt spa
								  fspa srat ept epa fepa erat n)

		(defun ang<2pi (ang)
			(if (and (<= 0 ang) (< ang (* 2 pi)))
				ang
				(ang<2pi (rem (+ ang (* 2 pi)) (* 2 pi)))
			)
		)
		;
		(defun 3dTo2dPt (pt) (list (car pt) (cadr pt)))
		;
		(defun tan (a) (/ (sin a) (cos a)))
		;
		(defun sublist (lst start leng / n r)
			(if (or (not leng) (< (- (length lst) start) leng))
				(setq leng (- (length lst) start))
			)
			(setq n (+ start leng))
			(while (< start n)
				(setq r (cons (nth (setq n (1- n)) lst) r))
			)
		)
		;
		(defun k*bulge (b k / a)
			(setq a (atan b))
			(/ (sin (* k a)) (cos (* k a)))
		)
		;
		; Main
		;
		(setq	;cl   (= (ang<2pi (vla-get-StartAngle el)) (ang<2pi (vla-get-EndAngle el)))
			cl   (equal (vlax-get el 'Startpoint) (vlax-get el 'Endpoint) 1e-6)
			norm (vlax-get el 'Normal)
			cen  (trans (vlax-get el 'Center) 0 norm)
			elv  (caddr cen)
			cen  (3dTo2dPt cen)
			pt0  (mapcar '+ (trans (vlax-get el 'MajorAxis) 0 norm) cen)
			ac0  (angle cen pt0)
			pt4  (mapcar '+ cen (trans (vlax-get el 'MinorAxis) 0 norm))
			pt2  (3dTo2dPt (trans (vlax-curve-getPointAtparam el (/ pi 4.)) 0 norm))
			ac4  (angle cen pt4)
			a04  (angle pt0 pt4)
			a02  (angle pt0 pt2)
			a24  (angle pt2 pt4)
			bsc0 (/ (ang<2pi (- a02 ac4)) 2.)
			bsc2 (/ (ang<2pi (- a04 a02)) 2.)
			bsc3 (/ (ang<2pi (- a24 a04)) 2.)
			bsc4 (/ (ang<2pi (- (+ ac0 pi) a24)) 2.)
			pt1  (inters pt0 (polar pt0 (+ ac0 (/ pi 2.) bsc0) 1.)
						 pt2 (polar pt2 (+ a02 bsc2) 1.)
						 nil)
			pt3  (inters pt2 (polar pt2 (+ a04 bsc3) 1.)
						 pt4 (polar pt4 (+ a24 bsc4) 1.)
						 nil)
			plst (list pt4 pt3 pt2 pt1 pt0)
			blst (mapcar '(lambda (b) (tan (/ b 2.)))
					 (list bsc4 bsc3 bsc2 bsc0)
				 )
		)
		(foreach b blst
			(setq blst (cons b blst))
		)
		(foreach b blst
			(setq blst (cons b blst))
		)
		(foreach p (cdr plst)
			(setq ang  (angle cen p)
				  plst (cons (polar cen (+ ang (* 2 (- ac4 ang))) (distance cen p)) plst)
			)
		)
		(foreach p (cdr plst)
			(setq ang  (angle cen p)
				  plst (cons (polar cen (+ ang (* 2 (- ac0 ang))) (distance cen p))	plst)
			)
		)
		(setq pl
			(vlax-invoke
				(vla-get-ModelSpace (vla-get-ActiveDocument (vlax-get-acad-object)))
				'AddLightWeightPolyline
				(apply 'append (setq	plst (reverse (if cl (cdr plst) plst))))
			)
		)
		(vlax-put pl 'Normal norm)
		(vla-put-Elevation pl elv)
		(mapcar '(lambda (i v) (vla-SetBulge pl i v))
		  '(0 1 2 3 4 5 6 7 8 9 10 11 12 13 14 15 16)
		  blst
		)
		(if cl
			(vla-put-Closed pl :vlax-true)
			(progn
				(setq spt	(vlax-curve-getClosestPointTo pl (vlax-get el 'Startpoint))
					  spa	(vlax-curve-getParamAtPoint pl spt)
					  fspa 	(fix spa)
					  ept	(vlax-curve-getClosestPointTo pl (vlax-get el 'Endpoint))
					  epa	(vlax-curve-getParamAtPoint pl ept)
					  fepa 	(fix epa)
					  n	 	0
				)
				(cond
					((equal spt (trans pt0 norm 0) 1e-9)
						(if (= epa fepa)
							(setq plst (sublist plst 0 (1+ fepa))
								  blst (sublist blst 0 (1+ fepa))
							)
							(setq erat (/ (- (vlax-curve-getDistAtParam pl epa)	(vlax-curve-getDistAtParam pl fepa))
										  (- (vlax-curve-getDistAtParam pl (rem (1+ fepa) 17)) (vlax-curve-getDistAtParam pl fepa))
										)
								  plst (append (sublist plst 0 (1+ fepa)) (list (3dTo2dPt (trans ept 0 norm))))
								  blst (append (sublist blst 0 (1+ fepa)) (list (k*bulge (nth fepa blst) erat)))
							)
						)
					)
					((equal ept (trans pt0 norm 0) 1e-9)
						(if (= spa fspa)
							(setq plst (sublist plst fspa nil)
								  blst (sublist blst fspa nil)
							)
							(setq srat (/ (- (vlax-curve-getDistAtParam pl (rem (1+ fspa) 17)) (vlax-curve-getDistAtParam pl spa))
										  (- (vlax-curve-getDistAtParam pl (rem (1+ fspa) 17)) (vlax-curve-getDistAtParam pl fspa))
										)
								  plst (cons (3dTo2dPt (trans spt 0 norm)) (sublist plst (1+ fspa) nil))
								  blst (cons (k*bulge (nth fspa blst) srat) (sublist blst (1+ fspa) nil))
							)
						)
					)
					(T
						(setq srat (/ (- (vlax-curve-getDistAtParam pl (rem (1+ fspa) 17)) (vlax-curve-getDistAtParam pl spa))
									  (- (vlax-curve-getDistAtParam pl (rem (1+ fspa) 17)) (vlax-curve-getDistAtParam pl fspa))
									)
							  erat (/ (- (vlax-curve-getDistAtParam pl epa) (vlax-curve-getDistAtParam pl fepa))
									  (- (vlax-curve-getDistAtParam pl (rem (1+ fepa) 17)) (vlax-curve-getDistAtParam pl fepa))
									)
						)
						(if (< epa spa)
							(setq plst 	(append (if (= spa fspa) 
													(sublist plst fspa nil) 
													(cons (3dTo2dPt (trans spt 0 norm)) (sublist plst (1+ fspa) nil))
												)
												(cdr (sublist plst 0 (1+ fepa))) (if (/= epa fepa)
																					 (list (3dTo2dPt (trans ept 0 norm)))
																				)
										)
								  blst 	(append (if (= spa fspa)
													(sublist blst fspa nil)
													(cons (k*bulge (nth fspa blst) srat) (sublist blst (1+ fspa) nil))
												)
												(sublist blst 0 fepa) (if (= epa fepa)
																		  (list (nth fepa blst))
																		  (list (k*bulge (nth fepa blst) erat))
																		)
										)
							)
							(setq plst (append	(if (= spa fspa)
													(sublist plst fspa (1+ (- fepa fspa)))
													(cons (3dTo2dPt (trans spt 0 norm)) (sublist plst (1+ fspa) (- fepa fspa)))
												)
												(list (3dTo2dPt (trans ept 0 norm)))
										)
								  blst (append 	(if (= spa fspa)
													(sublist blst fspa (- fepa fspa))
													(cons (k*bulge (nth fspa blst) srat) (sublist blst (1+ fspa) (- fepa fspa)))
												)
												(if (= epa fepa)
													(list (nth fepa blst))
													(list (k*bulge (nth fepa blst) erat))
												)
										)
							)
						)
					)
				)
				(vlax-put pl 'Coordinates (apply 'append plst))
				(foreach b blst
					(vla-SetBulge pl n b)
					(setq n (1+ n))
				)
			)
		)
		pl
	)
	;
	; Main
	;
	(setq acdoc (vla-get-ActiveDocument (vlax-get-acad-object)))
	(if (= (cdr (assoc 0 (entget Ename))) "ELLIPSE")
		(progn
			(vla-StartUndoMark acdoc)
			(if (setq Rtn (ElliToPoly (vlax-ename->vla-object Ename)))
				(if Flag (entdel Ename))
			)
			(vla-EndUndoMark acdoc)
		)
	)
	(if Rtn 
		(vlax-vla-object->ename Rtn)
		nil
	)
)



(defun Ellipse2LwPolyline01 (EnameEllipse Flag / old cen p1 p1n p2n sc old_PELLIPSE old_OSMODE)

  (setq old EnameEllipse)

    (setq cen (cdr (assoc 10 (entget old)))
           p1 (cdr (assoc 11 (entget old)))
          p1n (list (+ (car cen) (car p1))
                    (+ (cadr cen) (cadr p1))
                    (caddr cen))
          
          p2n (list (- (car cen) (car p1))
                    (- (cadr cen) (cadr p1))
                    (caddr cen))
          
          sc (cdr (assoc 40 (entget old)))
		  
          old_PELLIPSE (getvar "PELLIPSE")
          old_OSMODE   (getvar "OSMODE")
    )
    (setvar "PELLIPSE" 1)
    (setvar "OSMODE" 0)
    (if Flag (entdel EnameEllipse))
	
    (command "ELLIPSE" p1n p2n
			(polar cen (+ (angle cen p1n) (/ PI 2.0))
					   (* sc (distance cen p1n))
			)
    )
	(setq EnamePoly (entlast))
    (setvar "PELLIPSE" old_PELLIPSE)
    (setvar "OSMODE" old_OSMODE)
	(command "_ConvertPoly" "_Light" EnamePoly "")
	 EnamePoly
)
