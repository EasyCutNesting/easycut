Attribute VB_Name = "Module1"
Option Explicit

Public Const MAX_WIDTH = 1024
Public Const MAX_HEIGHT = 1024

Public VersionAutcad As String
Public AcCmColorAutocad As String

Private Type BitMapFile 'bitmap file header structure
bfType As String * 2
bfSize As String * 4
bfReserved1 As String * 2
bfreserved2 As String * 2
bfOffset As String * 4
End Type

Private Type BitMapInfo 'bitmap info header structure
biSize As String * 4
biWidth As String * 4
biHeight As String * 4
biPlanes As String * 2
biBitCount As String * 2
biCompression As String * 4
biSizeImage As String * 4
biXPelsPerMeter As String * 4
biYPelsPerMeter As String * 4
biClrUsed As String * 4
biClrImportant As String * 4
End Type

Private Type RGBQuads 'RGBQuad structure (temporary)
cBlue As String * 1
cGreen As String * 1
cRed As String * 1
cReserved As String * 1
End Type

Private Type RGBQuad 'RGBQuad (used in index)
Blue As Byte
Green As Byte
Red As Byte
End Type

Const PROCESS_QUERY_INFORMATION = &H400
Const SYNCHRONIZE = &H100000
Const INFINITE = &HFFFFFFFF
Const STILL_ACTIVE = &H103&
Const ERR_FILE_NOT_FOUND = 53

#If VBA7 Then
    ' 64 Bit API
    Declare PtrSafe Function OpenProcess Lib "kernel32" (ByVal dwDesiredAccess As Long, ByVal bInheritHandle As Long, ByVal dwProcessId As Long) As Long
    Declare PtrSafe Function GetExitCodeProcess Lib "kernel32" (ByVal hProcess As Long, lpExitCode As Long) As Long
    Declare PtrSafe Function GetTickCount Lib "kernel32" () As Long
    Declare PtrSafe Function InternetGetConnectedState Lib "wininet.dll" (ByRef lpdwFlags As Long, ByVal dwReserved As Long) As Long
#Else
    ' 32 bit API
    Declare Function OpenProcess Lib "kernel32" (ByVal dwDesiredAccess As Long, ByVal bInheritHandle As Long, ByVal dwProcessId As Long) As Long
    Declare Function GetExitCodeProcess Lib "kernel32" (ByVal hProcess As Long, lpExitCode As Long) As Long
    Declare Function GetTickCount64 Lib "kernel32" () As Long
    Declare Function InternetGetConnectedState Lib "wininet.dll" (lpdwFlags As Long, ByVal dwReserved As Long) As Boolean

#End If

'Declare PtrSafe Function OpenProcess64 Lib "kernel32" (ByVal dwDesiredAccess As Long, ByVal bInheritHandle As Long, ByVal dwProcessId As Long) As Long
'Declare PtrSafe Function GetExitCodeProcess64 Lib "kernel32" (ByVal hProcess As Long, lpExitCode As Long) As Long
'Private Declare Function OpenProcess Lib "kernel32" (ByVal dwDesiredAccess As Long, ByVal bInheritHandle As Long, ByVal dwProcessId As Long) As Long
'Private Declare Function GetExitCodeProcess Lib "kernel32" (ByVal hProcess As Long, lpExitCode As Long) As Long


Public Sub PixelationImage()

    VersionAutcad = showacadversion
    AcCmColorAutocad = "AutoCAD.AcCmColor." + VersionAutcad
    
    Dim NameImage As String
    Dim FileBmp As String
    Dim FileBat As String
    Dim returnPnt As Variant
  
    NameImage = Registry_Read("HKEY_CURRENT_USER\Software\EasyCut\Imaging\", "Key1")
    FileBmp = "EasyCutImage.bmp"
    FileBat = "EasyCutImage.bat"
       
    FileBat = ThisDrawing.GetVariable("SAVEFILEPATH") + FileBat
    FileBmp = ThisDrawing.GetVariable("SAVEFILEPATH") + FileBmp
    
    returnPnt = ThisDrawing.Utility.GetPoint(, "Punto inserimento : ")
   
    ShellConverImage NameImage, FileBmp, FileBat
    BitmapToAutocad FileBmp, returnPnt

End Sub

Public Sub ShowQrcode()

    VersionAutcad = showacadversion
    AcCmColorAutocad = "AutoCAD.AcCmColor." + VersionAutcad
    
    Dim NameQrcode As String
    Dim FilePng As String
    Dim FileBmp As String
    Dim FileVbs As String
    Dim FileBat As String
    Dim returnPnt As Variant
    
    FilePng = "EasyCutQrcode.png"
    FileBmp = "EasyCutQrcode.bmp"
    FileVbs = "EasyCutQrcode.vbs"
    FileBat = "EasyCutQrcode.bat"
    
    FilePng = ThisDrawing.GetVariable("SAVEFILEPATH") + FilePng
    FileBmp = ThisDrawing.GetVariable("SAVEFILEPATH") + FileBmp
    FileVbs = ThisDrawing.GetVariable("SAVEFILEPATH") + FileVbs
    FileBat = ThisDrawing.GetVariable("SAVEFILEPATH") + FileBat
    
    NameQrcode = Registry_Read("HKEY_CURRENT_USER\Software\EasyCut\Imaging\", "Key1")

    returnPnt = ThisDrawing.Utility.GetPoint(, "Punto inserimento : ")
    
    ShellQrcode NameQrcode, FilePng, FileBmp, FileVbs, FileBat
    BitmapToAutocad FileBmp, returnPnt

End Sub

Private Sub ShellQrcode(NameQrcode As String, FilePng As String, FileBmp As String, FileVbs As String, FileBat As String)

    Dim procID As Integer
    Dim hProcess As Long
    Dim lngRetval As Long
    Dim lngExitCode As Long
    Dim Exe As String
    
    Exe = Registry_Read("HKEY_CURRENT_USER\Software\EasyCut\Imaging\", "Key2")
    If NameQrcode <> "" Then
    
        Open FileVbs For Output As #1
        
            Print #1, "src =" + Chr(34) + "http://chart.googleapis.com/chart?cht=qr&chs=300x300&choe=UTF-8&chld=H&chl=" + NameQrcode + Chr(34)
            Print #1, "Set v1 = CreateObject (" + Chr(34) + "MSXML2.XMLHTTP" + Chr(34) + ")"
            Print #1, "Set v2  = CreateObject (" + Chr(34) + "ADODB.Stream" + Chr(34) + ")"
            Print #1, "v1.open " + Chr(34) + "GET" + Chr(34) + ", src, false"
            Print #1, "v1.send ()"
            Print #1, "v2.open"
            Print #1, "v2.Type = 1"
            Print #1, "v2.Write v1.ResponseBody"
            Print #1, "v2.SaveToFile " + Chr(34) + FilePng + Chr(34)
        
        Close #1
            
        Open FileBat For Output As #1
        
            Print #1, "@echo off"
            Print #1, "if exist " + Chr(34) + FilePng + Chr(34) + " del " + Chr(34) + FilePng + Chr(34)
            Print #1, "cscript " + Chr(34) + FileVbs + Chr(34)
            ' Print #1, "magick " + Chr(34) + FilePng + Chr(34) + " BMP3:" + Chr(34) + FileBmp + Chr(34)
            Print #1, Chr(34) + Exe + Chr(34) + " " + Chr(34) + FilePng + Chr(34) + " " + Chr(34) + "BMP3:" + FileBmp + Chr(34)
        Close #1
    End If
    procID = Shell(FileBat, vbHide)
    
    hProcess = OpenProcess(PROCESS_QUERY_INFORMATION Or SYNCHRONIZE, True, procID)
    Do
      ' Attempt to retrieve the exit code, which will
      ' just not exist until the application has quit.
      lngRetval = GetExitCodeProcess(hProcess, lngExitCode)
      DoEvents
    Loop Until lngExitCode <> STILL_ACTIVE
    
End Sub

Private Sub ShellConverImage(FileImage As String, FileBmp As String, FileBat As String)

    Dim procID As Long
    Dim hProcess As Long
    Dim lngRetval As Long
    Dim lngExitCode As Long
    Dim Exe As String
    
    Exe = Registry_Read("HKEY_CURRENT_USER\Software\EasyCut\Imaging\", "Key2")
    If FileImage <> "" Then
    
        Open FileBat For Output As #1
            Print #1, "@echo off"
            Print #1, "if exist " + Chr(34) + FileBmp + Chr(34) + " del " + Chr(34) + FileBmp + Chr(34)
            'Print #1, "magick.exe " + Chr(34) + FileImage + Chr(34) + " BMP3:" + Chr(34) + FileBmp + Chr(34)
            Print #1, Chr(34) + Exe + Chr(34) + " " + Chr(34) + FileImage + Chr(34) + " " + Chr(34); "BMP3:" + FileBmp + Chr(34)
        Close #1
    End If
    procID = Shell(FileBat, vbHide)
    hProcess = OpenProcess(PROCESS_QUERY_INFORMATION Or SYNCHRONIZE, True, procID)
    Do
      ' Attempt to retrieve the exit code, which will
      ' just not exist until the application has quit.
      lngRetval = GetExitCodeProcess(hProcess, lngExitCode)
      DoEvents
    Loop Until lngExitCode <> STILL_ACTIVE

End Sub

Public Function Registry_Write(Key_Path, Text) As Variant

    Dim Registry As Object
    Set Registry = CreateObject("WScript.Shell")
    Registry_Write = Registry.RegWrite(Key_Path, Text)
    
End Function

Public Function Registry_Read(Key_Path, Key_Name) As Variant

    Dim Registry As Object
    Set Registry = CreateObject("WScript.Shell")
    Registry_Read = Registry.RegRead(Key_Path & Key_Name)
    
End Function

Public Sub ShellHide()

    Dim procID As Integer
    Dim Application As String
    Application = Registry_Read("HKEY_CURRENT_USER\Software\EasyCut\Imaging\", "Key1")
    procID = Shell(Application, vbHide)
    
End Sub

Private Sub BitmapToAutocad(Filename As String, Pnt As Variant)

'Public Sub GetBmpValues(Filename As String, BMPData() As Long), Progress As MSForms.Label)

Dim bmf As BitMapFile
Dim bmi As BitMapInfo
Dim rgbqs As RGBQuads
Dim rgbq(255) As RGBQuad
Dim s1 As String * 1
Dim Dword As String * 4
Dim lngCol As Long
Dim lngRow As Long
Dim lngRow_ As Long
Dim IWidth As Long
Dim IBitCount As Integer
Dim Pointer As Long
Dim i As Integer
Dim ClrInd As Integer
Dim aMask As Long
Dim z As Integer
Dim ByteNum As Integer
Dim ThisByte As Byte
Dim ColoursFound As Integer
Dim ThisRed As Byte
Dim ThisGreen As Byte
Dim ThisBlue As Byte

Dim Xpoint As Long, Ypoint As Long, Zpoint As Long
Xpoint = Pnt(0): Ypoint = Pnt(1): Zpoint = 0


    Open Filename For Binary As #1
    
        Get #1, , bmf 'load the file header
        Get #1, , bmi 'info header follows
        
        
        If lVal(bmi.biSize) <> 40 Then
            MsgBox "[Errore] Versione Bitmap " & CStr(lVal(bmi.biSize)) & " non compatibile deve essere 40"
            Close #1
            Exit Sub
        End If
        
        If bmf.bfType <> "BM" Then
            MsgBox "[Errore] Formato non compatibile non è un bitmapfile"
            Close #1
            Exit Sub
        End If

        If lVal(bmi.biCompression) <> 0 Then
           MsgBox "[Errore] Bitmapfile compresso"
           Close #1
           Exit Sub
        End If
       
        If lVal(bmi.biWidth) > MAX_WIDTH Then
           MsgBox "[Errore] " & CStr(lVal(bmi.biWidth)) & " x " & CStr(lVal(bmi.biHeight)) & " Bitmap fuori formato Max " & CStr(MAX_WIDTH) & " x " & CStr(MAX_HEIGHT)
           Close #1
           Exit Sub
        End If
        
        If lVal(bmi.biHeight) > MAX_HEIGHT Then
           MsgBox "[Errore] " & CStr(lVal(bmi.biWidth)) & " x " & CStr(lVal(bmi.biHeight)) & " Bitmap fuori formato Max " & CStr(MAX_WIDTH) & " x " & CStr(MAX_HEIGHT)
           Close #1
           Exit Sub
        End If
       
        ThisDrawing.SendCommand "GRAPHSCR "
        ThisDrawing.Utility.Prompt vbCrLf & "Leggo BMP " & Filename
       
        'load the relevant colour tables
        
        If lVal(bmi.biBitCount) = 1 Then
        
            For i = 0 To 1
                Get #1, , rgbqs
                rgbq(i).Red = lVal(rgbqs.cRed)
                rgbq(i).Green = lVal(rgbqs.cGreen)
                rgbq(i).Blue = lVal(rgbqs.cBlue)
            Next i
            ElseIf lVal(bmi.biBitCount) = 4 Then
                For i = 0 To 15
                    Get #1, , rgbqs
                    rgbq(i).Red = lVal(rgbqs.cRed)
                    rgbq(i).Green = lVal(rgbqs.cGreen)
                    rgbq(i).Blue = lVal(rgbqs.cBlue)
                Next i
            ElseIf lVal(bmi.biBitCount) = 8 Then
                For i = 0 To 255
                    Get #1, , rgbqs
                    rgbq(i).Red = lVal(rgbqs.cRed)
                    rgbq(i).Green = lVal(rgbqs.cGreen)
                    rgbq(i).Blue = lVal(rgbqs.cBlue)
                Next i
        End If

       MsgBox "Actual File Size:" & (Str(LOF(1))) & " bytes" & vbCrLf & _
              "Bitmap Grandezza file: " & lVal(bmf.bfSize) & " bytes" & vbCrLf & _
              "Bitmap Larghezza: " & lVal(bmi.biWidth) & " pixels" & vbCrLf & _
              "Bitmap Altezza: " & lVal(bmi.biHeight) & " pixels" & vbCrLf & _
              "Bitmap Offset: " & lVal(bmf.bfOffset) & vbCrLf & _
              "Bitmap Formato: " & lVal(bmi.biSize) & vbCrLf & _
              "Bitmap BitPlanes: " & lVal(bmi.biPlanes) & vbCrLf & _
              "Bitmap BitCount: " & lVal(bmi.biBitCount) & " bit/pixel" & vbCrLf & _
              "Bitmap Colore: " & lVal(bmi.biSizeImage) & " bytes" & vbCrLf & _
              "Bitmap ClrUsed: " & lVal(bmi.biClrUsed) & vbCrLf & _
              "Bitmap ClrsImportant: " & lVal(bmi.biClrImportant) & vbCrLf & _
              "Bitmap Compressione: " & lVal(bmi.biCompression)

    Close #1



    If lVal(bmi.biBitCount) <= 8 Then
    
        ' the file is either:
        ' mono (1-bit/pixel)
        ' 16-color (4-bit/pixel)
        ' 256-color (8-bit/pixel)

        Open Filename For Binary As #1
            lngCol = 0 'holds X position of pixel to draw
            lngRow = lVal(bmi.biHeight) '- 1 'holds Y position (Note: bitmap stored from lowest line to highest)
            IWidth = lVal(bmi.biWidth) 'width of bitmap
            
            'Xpoint = 0
            'Ypoint = 0
            
            ReDim BMPData(lngRow, IWidth) As Long

            IBitCount = lVal(bmi.biBitCount) ' bits/pixel (1,4,8)
            Get #1, lVal(bmf.bfOffset), s1 'move binary pointer to start of bitmap
            
            Do While Not EOF(1)
                Get #1, , Dword ' read 4-bytes at a time
                ByteNum = 1 ' start with first byte in double word
                
                Do While lngCol < IWidth And ByteNum < 5 'stop drawing if edge of bitmap encountered or processed every byte in dword
                    ThisByte = lVal(Mid(Dword, ByteNum, 1)) 'get relevant byte
                    Pointer = 8 ' start bit pointer
                    
                    Do
                        If lngCol < IWidth Then 'only bother if edge of bitmap not reached
                            aMask = 0 'reset bit-mask
                    
                            For z = Pointer To Pointer - IBitCount + 1 Step -1 'the best algorithm
                                aMask = aMask + 2 ^ (z - 1) 'I could come up with to build a bit-mask
                            Next z
                            ClrInd = (ThisByte And (aMask)) / (2 ^ (Pointer - IBitCount)) ' mask of relevant bits and reduce to an appropriate index
                            
                            'BMPData(lngRow, lngCol + 1) = RGB(rgbq(ClrInd).Red, rgbq(ClrInd).Green, rgbq(ClrInd).Blue) 'set the pixel the colour
                            
                            CreatePoint CDbl(Xpoint), CDbl(Ypoint), CDbl(0), rgbq(ClrInd).Red, rgbq(ClrInd).Green, rgbq(ClrInd).Blue
                            Xpoint = Xpoint + 1
                            
                        End If
                
                        Pointer = Pointer - IBitCount 'move to the next appropriate bits
                        lngCol = lngCol + 1 'move the X-position
                        
                    Loop Until Pointer = 0 'not more bits to process - exit
                    
                    ByteNum = ByteNum + 1 'point to the next byte in the dword
                    
                Loop

                If lngCol >= IWidth Then 'if, after processing this dword, we have
                    ThisDrawing.Utility.Prompt vbCrLf & "Linee rimanenti " & lngRow

                    lngRow = lngRow - 1 'reached the end of a line then
                    Ypoint = Ypoint + 1
                    Xpoint = Pnt(0)
                    
                    If lngRow = 0 Then Exit Do
                    
                    lngCol = 0 'get the next line and reset the X-position
                End If
            Loop
        Close #1



    ElseIf lVal(bmi.biBitCount) = 24 Then
        '
        ' 16Million-color (24-bit/pixel)
        '
        Open Filename For Binary As #1
            lngCol = 0
            lngRow = lVal(bmi.biHeight) ' - 1
            IWidth = lVal(bmi.biWidth)
            
            'Xpoint = 0
            'Ypoint = 0
            
            ReDim BMPData(lngRow, IWidth) As Long
            IBitCount = lVal(bmi.biBitCount)
            Get #1, lVal(bmf.bfOffset), s1
            ColoursFound = 0 'need 3-colours to form a pixel
                    
            Do While Not EOF(1)
                Get #1, , Dword 'get 4-bytes
                ByteNum = 1
                        
                Do While lngCol < IWidth And ByteNum < 5
                    ThisByte = lVal(Mid(Dword, ByteNum, 1))
                    If lngCol < IWidth Then
                        ColoursFound = ColoursFound + 1
    
                        Select Case ColoursFound
                            
                            Case Is = 1 'first byte in three is blue (contradicts BMP.TXT)
                                ThisBlue = ThisByte
                            Case Is = 2 'second byte is green
                                ThisGreen = ThisByte
                            Case Is = 3 'third byte is red
                                ThisRed = ThisByte
                                'got the colours we need
                                'draw the pixel and move on to next pixel
                                
                                CreatePoint CDbl(Xpoint), CDbl(Ypoint), CDbl(0), ThisRed, ThisGreen, ThisBlue
                                'CreatePL CDbl(Xpoint), CDbl(Ypoint), CDbl(Xpoint), CDbl(Ypoint + 1), ThisRed, ThisGreen, ThisBlue
                                
                                Xpoint = Xpoint + 1
                                
                                'BMPData(lngRow, lngCol + 1) = RGB(ThisRed, ThisGreen, ThisBlue)
                                ColoursFound = 0
                                lngCol = lngCol + 1
                                
                                
                        End Select
                    End If
                    ByteNum = ByteNum + 1
                Loop
                        
                
                If lngCol >= IWidth Then
                    ThisDrawing.Utility.Prompt vbCrLf & "Linee rimanenti " & lngRow
                    lngRow = lngRow - 1
                    Ypoint = Ypoint + 1
                    Xpoint = Pnt(0)
                    If lngRow = 0 Then Exit Do
                        lngCol = 0
                    End If
            Loop
        Close #1
    End If

End Sub
Function lVal(vStr As String) As Long
    'convert little-endian string to long integer

    Dim i As Integer
    Dim t As Long
    t = 0
    For i = 1 To Len(vStr)
    t = t + Asc(Mid(vStr, i, 1)) * (256 ^ (i - 1))
    Next i
    lVal = t
    
End Function


Private Sub CreatePoint(x As Double, y As Double, z As Double, Red As Byte, Green As Byte, Blue As Byte)
  
  Dim pointObj As AcadPoint
  Dim location(0 To 2) As Double
  Dim Color As AcadAcCmColor
  
  Set Color = AcadApplication.GetInterfaceObject(AcCmColorAutocad)
  
  
  Color.SetRGB Red, Green, Blue
  location(0) = x: location(1) = y: location(2) = 0#

  Set pointObj = ThisDrawing.ModelSpace.AddPoint(location)
  pointObj.TrueColor = Color
  
  
  
End Sub

Private Sub CreatePL(xi As Double, yi As Double, _
                     xf As Double, yf As Double, _
                     Red As Byte, Green As Byte, Blue As Byte)
  
  Dim plineObj As AcadLWPolyline
  Dim points(0 To 3) As Double
  Dim Color As AcadAcCmColor
  
  Set Color = AcadApplication.GetInterfaceObject(AcCmColorAutocad)
  Call Color.SetRGB(Red, Green, Blue)

  points(0) = xi: points(1) = yi
  points(2) = xf: points(3) = yf

  Set plineObj = ThisDrawing.ModelSpace.AddLightWeightPolyline(points)
  plineObj.ConstantWidth = 1
  plineObj.TrueColor = Color
  
End Sub

Public Function showacadversion() As String

    'AutoCAD 2007    17.0    AC1021
    'AutoCAD 2008    17.1    AC1021
    'AutoCAD 2009    17.2    AC1021
    'AutoCAD 2010    18.0    AC1024
    'AutoCAD 2011    18.1    AC1024
    'AutoCAD 2012    18.2    AC1024
    'AutoCAD 2013    19.0    AC1027
    'AutoCAD 2014    19.1    AC1027
    'AutoCAD 2015    20.0    AC1027
    'AutoCAD 2016    20.1    AC1027
    'AutoCAD 2017    21.0    AC1027
    'AutoCAD 2018    22.0    AC1032

    Dim strArray() As String
    
    'showacadversion = Left(AutoCAD.Application.ActiveDocument.GetVariable("acadver"), 4)
    showacadversion = ThisDrawing.GetVariable("acadver")
    strArray = Split(showacadversion, ".")
    showacadversion = strArray(0)
    
End Function

Public Sub wait(ByVal dblMilliseconds As Double)
    Dim dblStart As Double
    Dim dblEnd As Double
    Dim dblTickCount As Double
    
    'dblTickCount = GetTickCount64()
    'dblStart = GetTickCount64()
    'dblEnd = GetTickCount64() + dblMilliseconds
    
    'Do
        'DoEvents
    '    dblTickCount = GetTickCount64()
    'Loop Until dblTickCount > dblEnd Or dblTickCount < dblStart
       
    dblTickCount = GetTickCount()
    dblStart = GetTickCount()
    dblEnd = GetTickCount() + dblMilliseconds
    
    Do
    'DoEvents
    dblTickCount = GetTickCount()
    Loop Until dblTickCount > dblEnd Or dblTickCount < dblStart
       
    
End Sub

Attribute VB_Name = "Module2"
'Local system uses a modem to connect to the Internet.
Const INTERNET_CONNECTION_MODEM As Long = &H1
'Local system uses a LAN to connect to the Internet.
Const INTERNET_CONNECTION_LAN As Long = &H2
'Local system uses a proxy server to connect to the Internet.
Const INTERNET_CONNECTION_PROXY As Long = &H4
'No longer used.
Const INTERNET_CONNECTION_MODEM_BUSY As Long = &H8
Const INTERNET_RAS_INSTALLED As Long = &H10
Const INTERNET_CONNECTION_OFFLINE As Long = &H20
Const INTERNET_CONNECTION_CONFIGURED As Long = &H40
'
' Interntet Check
'
Public Sub InternetStatus()

        Dim CurrentUser As String
        Dim EasyCutRegistry As String
        Dim Rtn As String
                
        Rtn = ""
        CurrentUser = "HKEY_CURRENT_USER\"
        EasyCutRegistry = "Software\EasyCut\Internet"
      
        If IsNetConnectViaLAN() Then
            'Console.WriteLine("Lan    -> OK")
            Rtn = Rtn + "Lan OK|"
        Else
            'Console.WriteLine("Lan    -> NO")
            Rtn = Rtn + "Lan NO|"
        End If
        If IsNetConnectViaModem() Then
            'Console.WriteLine("Modem  -> OK")
            Rtn = Rtn + "Modem OK|"
        Else
            'Console.WriteLine("Modem  -> NO")
            Rtn = Rtn + "Modem NO|"
        End If
        If IsNetConnectViaProxy() Then
            'Console.WriteLine("Proxy  -> OK")
            Rtn = Rtn + "Proxy OK|"
        Else
            'Console.WriteLine("Proxy  -> NO")
            Rtn = Rtn + "Proxy NO|"
        End If
        If IsNetConnectOnline() Then
            'Console.WriteLine("OnLine -> OK")
            Rtn = Rtn + "OnLine OK|"
        Else
            'Console.WriteLine("OnLine -> NO")
            Rtn = Rtn + "OnLine NO|"
        End If
        If IsNetRASInstalled() Then
            'Console.WriteLine("RAS    -> OK Remote Access Services")
            Rtn = Rtn + "RAS OK|"
        Else
            'Console.WriteLine("RAS    -> NO Remote Access Services")
            Rtn = Rtn + "RAS NO|"
        End If
        Rtn = Rtn + GetNetConnectString()
        'Console.WriteLine(Status)
         Registry_Write CurrentUser + EasyCutRegistry, Rtn
    End Sub


Public Function IsNetConnectViaLAN() As Boolean

     Dim dwflags As Long

     'pass an empty variable into which the API will
     'return the flags associated with the connection
     Call InternetGetConnectedState(dwflags, 0&)

     'return True if the flags indicate a LAN connection
     IsNetConnectViaLAN = dwflags And INTERNET_CONNECTION_LAN
End Function
Public Function IsNetConnectViaModem() As Boolean

     Dim dwflags As Long

     'pass an empty variable into which the API will
     'return the flags associated with the connection
     Call InternetGetConnectedState(dwflags, 0&)

     'return True if the flags indicate a modem connection
     IsNetConnectViaModem = dwflags And INTERNET_CONNECTION_MODEM
End Function
Public Function IsNetConnectViaProxy() As Boolean

     Dim dwflags As Long

     'pass an empty variable into which the API will
     'return the flags associated with the connection
     Call InternetGetConnectedState(dwflags, 0&)

     'return True if the flags indicate a proxy connection
     IsNetConnectViaProxy = dwflags And INTERNET_CONNECTION_PROXY
End Function
Public Function IsNetConnectOnline() As Boolean

     'no flags needed here - the API returns True
     'if there is a connection of any type
     IsNetConnectOnline = InternetGetConnectedState(0&, 0&)

End Function
Public Function IsNetRASInstalled() As Boolean

     Dim dwflags As Long

     'pass an empty variable into which the API will
     'return the flags associated with the connection
     Call InternetGetConnectedState(dwflags, 0&)

     'return True if the flags include RAS installed
     IsNetRASInstalled = dwflags And INTERNET_RAS_INSTALLED

End Function
Public Function GetNetConnectString() As String

     Dim dwflags As Long
     Dim msg As String
     msg = ""

     'build a string for display
     If InternetGetConnectedState(dwflags, 0&) Then

         If dwflags And INTERNET_CONNECTION_CONFIGURED Then
             msg = msg & "You have a network connection configured."
         End If

         If dwflags And INTERNET_CONNECTION_LAN Then
             msg = msg & "The local system connects to the Internet via a LAN"
         End If

         If dwflags And INTERNET_CONNECTION_PROXY Then
             msg = msg & ", and uses a proxy server. "
         Else
             msg = msg & "."
         End If

         If dwflags And INTERNET_CONNECTION_MODEM Then
             msg = msg & "The local system uses a modem to connect to the Internet. "
         End If

         If dwflags And INTERNET_CONNECTION_OFFLINE Then
             msg = msg & "The connection is currently offline[NoInt]."
         End If

         If dwflags And INTERNET_CONNECTION_MODEM_BUSY Then
             msg = msg & "The local system's modem is busy with a non-Internet connection.[NoInt]"
         End If

         If dwflags And INTERNET_RAS_INSTALLED Then
             msg = msg & "Remote Access Services are installed on this system."
         End If

     Else

         msg = "Not connected to the internet[NoInt]"

     End If

     GetNetConnectString = msg

End Function
