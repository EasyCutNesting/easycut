(defun text-box ( enx off / mxv b h j l m n o p r w )

	;; Text Box  -  gile / Lee Mac
	;; Returns an OCS point list describing a rectangular frame surrounding
	;; the supplied text or mtext entity with optional offset
	;; enx - [lst] Text or MText DXF data list
	;; off - [rea] offset (may be zero)
	
	;; Matrix x Vector  -  Vladimir Nesterovsky
	;; Args: m - nxn matrix, v - vector in R^n
	(defun mxv ( m v )
		(mapcar '(lambda ( r ) (apply '+ (mapcar '* r v))) m)
	)
	;
	;Main
	;
    (if
        (setq l
            (cond
                (   (= "TEXT" (cdr (assoc 0 enx)))
                    (setq b (cdr (assoc 10 enx))
                          r (cdr (assoc 50 enx))
                          l (textbox enx)
                    )
                    (list
                        (list (- (caar  l) off) (- (cadar  l) off))
                        (list (+ (caadr l) off) (- (cadar  l) off))
                        (list (+ (caadr l) off) (+ (cadadr l) off))
                        (list (- (caar  l) off) (+ (cadadr l) off))
                    )
                )
                (   (= "MTEXT" (cdr (assoc 0 enx)))
                    (setq n (cdr (assoc 210 enx))
                          b (trans  (cdr (assoc 10 enx)) 0 n)
                          r (angle '(0.0 0.0 0.0) (trans (cdr (assoc 11 enx)) 0 n))
                          w (cdr (assoc 42 enx))
                          h (cdr (assoc 43 enx))
                          j (cdr (assoc 71 enx))
                          o (list
                                (cond
                                    ((member j '(2 5 8)) (/ w -2.0))
                                    ((member j '(3 6 9)) (- w))
                                    (0.0)
                                )
                                (cond
                                    ((member j '(1 2 3)) (- h))
                                    ((member j '(4 5 6)) (/ h -2.0))
                                    (0.0)
                                )
                            )
                    )
                    (list
                        (list (- (car o)   off) (- (cadr o)   off))
                        (list (+ (car o) w off) (- (cadr o)   off))
                        (list (+ (car o) w off) (+ (cadr o) h off))
                        (list (- (car o)   off) (+ (cadr o) h off))
                    )
                )
            )
        )
        (   (lambda ( m ) (mapcar '(lambda ( p ) (mapcar '+ (mxv m p) b)) l))
            (list
                (list (cos r) (sin (- r)) 0.0)
                (list (sin r) (cos r)     0.0)
               '(0.0 0.0 1.0)
            )
        )
    )
)
;
;
(defun GeoText (EnameText / InfoText)
	(if EnameText
		(progn
			(setq InfoText (text-box (entget EnameText) 0.0))
			(list (distance (car InfoText)  (cadr InfoText))
				  (distance (cadr InfoText) (caddr InfoText)))	
		)
	)
)
;
;(defun Test ()
;	(setq EnameText (car (entsel)))
;   (setq e (entget EnameText)
;          l (text-box e (/ (cdr (assoc 40 e)) 2.0))
;   )
;    (entmod (append e '((62 . 1))))
;    (mapcar '(lambda ( a b ) (grdraw a b 1 1)) l (cons (last l) l))
;)
