(defun c:demo (/ imagefile inimage)
  (if (findfile (Setq imagefile "C:\\deluca\\EasyCutBeta\\Output\\Docs\\_857264222_.png"))
    (progn
	  (setq	inimage	(vlax-invoke
			  (vlax-get
			    (vla-get-ActiveLayout
			      (vla-get-activedocument
				(vlax-get-acad-object)
			      )
			    )
			    'Block
			  )
			  'AddRaster
			  imagefile	
			  '(0.0 0.0 0.0)
			  44.5			;<-width
			  0.0
			)
	  )
	  ;(vla-put-name inimage "MyInsertedPicture") ;<-- Name 
	  ;(vla-update inimage)
      )
    )
  (princ)
)

(vl-load-com)
(defun C:imagetotxt (/)
 (setq image (vla-get-ImageFile (vlax-ename->vla-object (car (entsel "\nSelect Image:")))))
 (setq start1 (getvar "CDATE"))
 (setq stream (vlax-get-or-create-object "ADODB.stream"))
 (vlax-put-property stream 'type 1)
 (vlax-invoke stream 'open)
 (vlax-invoke stream 'loadfromfile image)
 (vlax-put-property stream 'position 0)
 (setq size (vlax-get stream 'size))
 (setq variable (cond ((< size 10000)10)
        ((< size 100000)100)
        ((< size 1000000)10000)
        ((< size 10000000)100000)
        ((< size 100000000)10000000)
        ((< size 1000000000)100000000)))
 (setq count 0)
 (setq text (vlax-variant-value (vlax-invoke-method stream 'read (vlax-get stream 'size))))
 (setq hextext nil)
 (setq hexbatch nil)
 (setq finalhextext nil)
 (setq countcol 0)
 (setq colmax 256)
 (setq countdata 0)
 (setq datamax 256)
 (while (< count size)
   (setq hextext (append hextext (list (DecToHex (vlax-safearray-get-element text count)))))
   (setq count (+ count 1))
   (setq countdata (+ countdata 1))
   (if (= countdata datamax)
     (progn
(setq hexbatch (append hexbatch (list hextext)))
(setq hextext nil)
(setq countcol (+ countcol 1))
(setq countdata 0)
)
     )
   (if (= countcol colmax)
     (progn
(setq finalhextext (append finalhextext (list hexbatch)))
(setq hexbatch nil)
(setq countcol 0)
)
     )
   (if (= (rem count (/ size variable)) 0)
     (print (strcat "ETA:" (rtos (*(/(*(- (setq finish2 (getvar "CDATE")) start1)1000000)count)(-(* 1.0 size) count)))))
     )
   )
 (setq hexbatch (append hexbatch (list hextext)))
 (setq finalhextext (append finalhextext (list hexbatch)))
 (setq finish1 (getvar "CDATE"))
 (alert (strcat "Image to hex: " (rtos (*(- finish1 start1)1000000))))
 (print (strcat "File Size: " (itoa (hexcounter (strcat(offset 2 finalhextext) " " (offset 3 finalhextext) " " (offset 4 finalhextext) " " (offset 5 finalhextext))))))
 (print (strcat "Pixel Array starts at: "  (itoa (hexcounter (strcat(offset 10 finalhextext) " " (offset 11 finalhextext) " " (offset 12 finalhextext) " " (offset 13 finalhextext))))))
(print (strcat "Width: " (itoa (hexcounter (strcat (offset 18 finalhextext) " " (offset 19 finalhextext) " " (offset 20 finalhextext) " " (offset 21 finalhextext))))))
 (print (strcat "Hight:"  (itoa (hexcounter (strcat(offset 22 finalhextext) " " (offset 23 finalhextext) " " (offset 24 finalhextext) " " (offset 25 finalhextext))))))
 (print (strcat "Number of Color Planes:"  (itoa (hexcounter (strcat(offset 26 finalhextext) " " (offset 27 finalhextext))))))
 (print (strcat "Bits Per Pixel:"  (itoa (hexcounter (strcat(offset 28 finalhextext) " " (offset 29 finalhextext))))))
 (print (strcat "Pixel Array Compression:"  (itoa (hexcounter (strcat(offset 30 finalhextext) " " (offset 31 finalhextext) " " (offset 32 finalhextext) " " (offset 33 finalhextext))))))
 (print (strcat "Size of Raw pixel Data:"  (itoa (hexcounter (strcat(offset 34 finalhextext) " " (offset 35 finalhextext) " " (offset 36 finalhextext) " " (offset 37 finalhextext))))))
 )
(defun DecToHex (int /)
 (setq int (cond ((> int 256)(rem int 256))
   ((< int 0)(+(rem int 256) 256))
   (t int))
)
 (if (= int 256)
   "00"
   (progn
     (setq b (rem int 16))
     (setq a (/ (- int b) 16))
     (strcat (if (< a 10)(itoa a)(chr (+ 55 a))) (if (< b 10)(itoa b)(chr (+ 55 b))))
     )
   )
 )
(defun HexToDec (str /)
 (setq a (substr str 1 1))
 (setq b (substr str 2 1))
 
 (if (wcmatch a "@")
   (setq a (- (vl-string-elt a 0) 55))
   (setq a (atoi a))
   )
 (if (wcmatch b "@")
   (setq b (- (vl-string-elt b 0) 55))
   (setq b (atoi b))
   )
 (princ (+(* a 16) b))
 )
(defun 3Ddata (row col data source)
 (nth data (nth col (nth row source)))
)
(defun offset (digit source)
 (setq row (/ (- digit (rem digit 65536)) 65536))
 (setq digit (- digit (* row 65536)))
 (setq col (/ (- digit (rem digit 256)) 256))
 (setq digit (- digit (* col 256)))
 (setq data digit)
 (3ddata row col data source)
 )
(defun hexcounter (string)
 (while (wcmatch string "* *")(setq string (vl-string-subst "" " " string)))
 (setq len (strlen string))
 (setq strcount 0)
 (setq hexarray nil)
 (setq value 0)
 (setq arraypower 0)
 (while (< strcount len)
   (setq hexarray (append hexarray (list (substr string (+ strcount 1) 2))))
   (setq strcount (+ strcount 2))
   )
 (foreach hexbyte hexarray
   (setq value (+ value (* (hextodec hexbyte) (expt 256 arraypower))))
   (setq arraypower (+ arraypower 1))
   )
 value
 )
