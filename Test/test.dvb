Attribute VB_Name = "Module1"
Option Explicit

Public Const MAX_WIDTH = 1024
Public Const MAX_HEIGHT = 1024

Public VersionAutcad As String
Public AcCmColorAutocad As String

Private Type BitMapFile 'bitmap file header structure
bfType As String * 2
bfSize As String * 4
bfReserved1 As String * 2
bfreserved2 As String * 2
bfOffset As String * 4
End Type

Private Type BitMapInfo 'bitmap info header structure
biSize As String * 4
biWidth As String * 4
biHeight As String * 4
biPlanes As String * 2
biBitCount As String * 2
biCompression As String * 4
biSizeImage As String * 4
biXPelsPerMeter As String * 4
biYPelsPerMeter As String * 4
biClrUsed As String * 4
biClrImportant As String * 4
End Type

Private Type RGBQuads 'RGBQuad structure (temporary)
cBlue As String * 1
cGreen As String * 1
cRed As String * 1
cReserved As String * 1
End Type

Private Type RGBQuad 'RGBQuad (used in index)
Blue As Byte
Green As Byte
Red As Byte
End Type

Const PROCESS_QUERY_INFORMATION = &H400
Const SYNCHRONIZE = &H100000
Const INFINITE = &HFFFFFFFF
Const STILL_ACTIVE = &H103&
Const ERR_FILE_NOT_FOUND = 53

#If VBA7 = True Then
    MsgBox ("VBA7")
    ' 64 Bit API
    'Private Declare PtrSafe Function OpenProcess Lib "kernel32" (ByVal dwDesiredAccess As Long, ByVal bInheritHandle As Long, ByVal dwProcessId As Long) As LongPtr
    'Private Declare PtrSafe Function GetExitCodeProcess Lib "kernel32" (ByVal hProcess As LongPtr, lpExitCode As Long) As Long
    'Declare PtrSafe Function GetTickCount64 Lib "kernel32" () As LongLong
    'Public Declare PtrSafe Function InternetGetConnectedState Lib "wininet.dll" (lpdwFlags As LongPtr, ByVal dwReserved As Long) As Boolean
#Else
    MsgBox ("Altro")
    ' 32 bit API
    'Declare Func   tion OpenProcess Lib "kernel32" (ByVal dwDesiredAccess As Long, ByVal bInheritHandle As Long, ByVal dwProcessId As Long) As Long
    'Declare Function GetExitCodeProcess Lib "kernel32" (ByVal hProcess As Long, lpExitCode As Long) As Long
    'Declare Function GetTickCount Lib "kernel32" () As Long
    'Declare Function InternetGetConnectedState Lib "wininet.dll" (ByRef lpdwFlags As Long, ByVal dwReserved As Long) As Long
#End If
