(defun LoadBin (Path)
	(if Path
		(progn
			(MyLoad (strcat Path "\\Bin\\AcadBridge.lsp"	))
			(PrgBr NfileLsp$)
			(MyLoad (strcat Path "\\Bin\\Entity.lsp"	    ))
			(PrgBr NfileLsp$)
			(MyLoad (strcat Path "\\Bin\\ShapeEntity.lsp"   ))
			(PrgBr NfileLsp$)
			(MyLoad (strcat Path "\\Bin\\GetFilesV1-6.lsp"	))
			(PrgBr NfileLsp$)
			(MyLoad (strcat Path "\\Bin\\Cut.lsp"			))
			(PrgBr NfileLsp$)
			(MyLoad (strcat Path "\\Bin\\ToolMove.lsp"		))
			(PrgBr NfileLsp$)
			(MyLoad (strcat Path "\\Bin\\PointTrigger.lsp"	))
			(PrgBr NfileLsp$)
			(MyLoad (strcat Path "\\Bin\\PostProcessor.lsp"	))
			(PrgBr NfileLsp$)
			(MyLoad (strcat Path "\\Bin\\Dinfo.lsp"			))
			(PrgBr NfileLsp$)
			(MyLoad (strcat Path "\\Bin\\Dimension.lsp"		))
			(PrgBr NfileLsp$)
			(MyLoad (strcat Path "\\Bin\\Symula.lsp"		))
			(PrgBr NfileLsp$)
			(MyLoad (strcat Path "\\Bin\\LeanOn.lsp"		))
			(PrgBr NfileLsp$)
			(MyLoad (strcat Path "\\Bin\\ImportDstv.lsp"	))
			(PrgBr NfileLsp$)
			(MyLoad (strcat Path "\\Bin\\ImportCam.lsp"	    ))
			(PrgBr NfileLsp$)
			(MyLoad (strcat Path "\\Bin\\ImportDxf.lsp"	    ))
			(PrgBr NfileLsp$)
			(MyLoad (strcat Path "\\Bin\\Tools1.lsp"        ))
			(PrgBr NfileLsp$)
			(MyLoad (strcat Path "\\Bin\\Tools2.lsp"        ))
			(PrgBr NfileLsp$)
			(MyLoad (strcat Path "\\Bin\\Utility.lsp"       ))
			(PrgBr NfileLsp$)
			(MyLoad (strcat Path "\\Bin\\UtilityLeeMac.lsp" ))
			(PrgBr NfileLsp$)
			(MyLoad (strcat Path "\\Bin\\DummyNesting.lsp"	))
			(PrgBr NfileLsp$)
			(MyLoad (strcat Path "\\Bin\\Math.lsp"			))
			(PrgBr NfileLsp$)
			(MyLoad (strcat Path "\\Bin\\Micro.lsp"			))
			(PrgBr NfileLsp$)
			(MyLoad (strcat Path "\\Bin\\BarCode.lsp"		))
			(PrgBr NfileLsp$)
			(MyLoad (strcat Path "\\Bin\\Nesting.lsp"		))
			(PrgBr NfileLsp$)
			(MyLoad (strcat Path "\\Bin\\PowerShellDiag.lsp"))
			(PrgBr NfileLsp$)
			(MyLoad (strcat Path "\\Bin\\Reactors.lsp"		))
			(PrgBr NfileLsp$)
			(MyLoad (strcat Path "\\Bin\\Query.lsp"			))
			(PrgBr NfileLsp$)
			(MyLoad (strcat Path "\\Bin\\Group.lsp"			))
			(PrgBr NfileLsp$)
			(MyLoad (strcat Path "\\Bin\\QrCode.lsp"		))
			(PrgBr NfileLsp$)
			(MyLoad (strcat Path "\\Bin\\Xref.lsp"			))
			(PrgBr NfileLsp$)
			(MyLoad (strcat Path "\\Bin\\ExcelLib.lsp"		))
			(PrgBr NfileLsp$)
			(MyLoad (strcat Path "\\Bin\\ImportXlsCsv.lsp"	))
			(PrgBr NfileLsp$)
			(MyLoad (strcat Path "\\Bin\\DinamicAllign.lsp"	))
			(PrgBr NfileLsp$)
			(MyLoad (strcat Path "\\Bin\\Flex.lsp"			))
			(PrgBr NfileLsp$)
			(MyLoad (strcat Path "\\Bin\\Codex.lsp"			))
			(PrgBr NfileLsp$)
			(MyLoad (strcat Path "\\Bin\\DxfNest.lsp"		))
			(PrgBr NfileLsp$)
			(MyLoad (strcat Path "\\Bin\\RectPack.lsp"		))
			(PrgBr NfileLsp$)
			(MyLoad (strcat Path "\\Bin\\DxfToEntmake.lsp"))
			(PrgBr NfileLsp$)
			; nesting Bar +++++++++++++++++++++++++++++++++++++
			(MyLoad (strcat Path "\\Bin\\AdlNesting.lsp"	))
			(PrgBr NfileLsp$)
			(MyLoad (strcat Path "\\Bin\\BinpackCut.lsp"	))
			(PrgBr NfileLsp$)
			(MyLoad (strcat Path "\\Bin\\EpCut.lsp"			))
			(PrgBr NfileLsp$)
			(MyLoad (strcat Path "\\Bin\\LdCsp.lsp"			))
			(PrgBr NfileLsp$)
			(MyLoad (strcat Path "\\Bin\\NestingBars.lsp"))
			(PrgBr NfileLsp$)
			(MyLoad (strcat Path "\\Bin\\ResolutionNestingBar.lsp"))
			(PrgBr NfileLsp$)
			(MyLoad (strcat Path "\\Bin\\TableNestingBar.lsp"))
			(PrgBr NfileLsp$)
			(MyLoad (strcat Path "\\Bin\\RoyCut.lsp"		))
			(PrgBr NfileLsp$)
			;(MyLoadVba (strcat Path "\\Bin\\BitmapMapping.dvb"))
			;(PrgBr NfileLsp$)
		)
	)
	(princ)
)
