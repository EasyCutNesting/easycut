(defun LoadGui (Path)

	(if Path
		(progn
			(MyLoad (strcat Path "\\Gui\\Setup.lsp"))
			(PrgBr NfileLsp$)
			(MyLoad (strcat Path "\\Gui\\GuiShape.lsp"))
			(PrgBr NfileLsp$)
			(MyLoad (strcat Path "\\Gui\\DialogBox.lsp"))
			(PrgBr NfileLsp$)
			(MyLoad (strcat Path "\\Gui\\GuiSheet.lsp"))
			(PrgBr NfileLsp$)
			(MyLoad (strcat Path "\\Gui\\SetColor.lsp"))
			(PrgBr NfileLsp$)
			(MyLoad (strcat Path "\\Gui\\Zoom.lsp"))
			(PrgBr NfileLsp$)
			(MyLoad (strcat Path "\\Gui\\HatchShape.lsp"))
			(PrgBr NfileLsp$)
			(MyLoad (strcat Path "\\Gui\\TraceShape.lsp"))
			(PrgBr NfileLsp$)
			(MyLoad (strcat Path "\\Gui\\MenuEC.lsp"))
			(PrgBr NfileLsp$)
			(MyLoad (strcat Path "\\Gui\\StartUp.lsp"))
			(PrgBr NfileLsp$)
			(MyLoad (strcat Path "\\Gui\\GetFiled.lsp"))
			(PrgBr NfileLsp$)
			(MyLoad (strcat Path "\\Gui\\OpenFileDialog.lsp"))
			(PrgBr NfileLsp$)
			(MyLoad (strcat Path "\\Gui\\FormsOpenFileDialog.lsp"))
			(PrgBr NfileLsp$)
			(MyLoad (strcat Path "\\Gui\\Command.lsp"))
			(PrgBr NfileLsp$)
			(MyLoad (strcat Path "\\Gui\\PopListMacro.lsp"))
			(PrgBr NfileLsp$)
			(MyLoad (strcat Path "\\Gui\\EasyCutViewer.lsp"))
			(PrgBr NfileLsp$)
		)
	)
	(princ)
)
