(defun ReportFound (LstFoundSearch / Swap
									TotQta TotWgt NameReport Stream Num Mark EnameRef Dim Surface Weight
									Sheet EnameSheet DataSheet DataCut LstDataFound conta IdRnd
									&Date &Time &JobNumber &SheetOrder &SheetId &SheetDim &SheetMat &SheetWidth 
									&SheetHeight &SheetThikness &SheetSurface &SheetWeight &SheetSpeedCut &ShapeTotLgCut
									$ShapeTimingCut &ShapeSurface &ShapeWeight &SheetScrapsSurface &SheetScrapsWeigth &SheetScrapsPercent
									&ShapeOrder	&ShapePhase &ShapeName &ShapeMat &ShapeTk &ShapeQta &ShapeDim &ShapeWeight &ShapeTotWeight &ShapeBarCode)
	
	;( (EnameSheet ("Com|Phase|Name" EnameShape EnameShape) 
	;		   	   ("Com|Phase|Name" EnameShape EnameShape) ....) 
	;  (EnameSheet ("Com|Phase|Name" EnameShape EnameShape))
	;)
	;
	(defun Swap (DatoA DatoB Indice / Rtn)
	
		(if (> (- (/ Indice 2.0) (fix (/ Indice 2.0))) 0)
			(setq Rtn DatoB)
			(setq Rtn DatoA)
		)
	)	
	;
	; Main
	;
	(setq Color1 "#DDEBF7")
	(setq Color2 "#BDD7EE")
	
	(setq NameReport (strcat HtmlStorageEasyCut$ ECFolderReport$ "Found.html"))
	(setq Stream (open NameReport "w")) 
	(if Stream
		(progn
			(StartProgressBar "Report" (length LstFoundSearch))
			(princ "<!DOCTYPE html PUBLIC \"-//W3C//DTD XHTML 1.0 Transitional//EN\" \"http://www.w3.org/TR/xhtml1/DTD/xhtml1-transitional.dtd\">\n" Stream)
			(princ "<html xmlns=\"http://www.w3.org/1999/xhtml\">\n" 																Stream)
			(princ "<head>\n" 																										Stream)
			(princ "<meta http-equiv=\"Content-Type\" content=\"text/html; charset=iso-8859-1\" />\n" 								Stream)
			(princ (strcat "<link rel=\"stylesheet\" type=\"text/css\" href=\"" TmpScrHtmlEasyCut$ "normalize.css\" />\n")			Stream)
			(princ "<title>Untitled Document</title>\n" 																			Stream)
			(princ "<style type=\"text/css\">\n"																					Stream)
			(princ ".wrapper          {width:100%;margin-left:auto;margin-right:auto;font-family:Arial;}\n"							Stream)
			(princ ".print            {font-size:12px; float: left;}\n"																Stream)
			(princ ".title            {font-size:18px}\n"																			Stream)
			(princ ".infocatlist      {margin-top:5px;}\n"																			Stream)
			(princ ".td               {font-size: 9pt;}\n"																			Stream)
			(princ ".barcode          {margin-top: 5px;}\n"																			Stream)
			(princ "@page             {size: 210mm 297mm; margin: 5mm;}\n"															Stream)
			(princ "tr                {page-break-inside: avoid;}\n"																Stream)
			(princ ".header		      {}\n"																							Stream)
			(princ ".logo	          {float: right; height: 45px;}\n"																Stream)
			(princ ".logo img	      {height: 45px; display: inline-block;}\n"														Stream)
			(princ ".clearfix:after   {visibility: hidden; display: block; font-size: 0; content: \" \"; clear: both; height: 0;}\n" Stream)
			(princ "* html .clearfix  {zoom: 1;} /* IE6 */\n"																		Stream)
			(princ "*:first-child+html .clearfix {zoom: 1;} /* IE7 */\n"															Stream)
			(princ "</style>\n"																										Stream)
			(princ (strcat "<script type=\"text/javascript\" src=\"" TmpScrHtmlEasyCut$ "jquery-1.3.2.min.js\"></script>\n")		Stream)
			(princ (strcat "<script type=\"text/javascript\" src=\"" TmpScrHtmlEasyCut$ "jquery-barcode-2.0.2.min.js\"></script>\n")Stream)				
			(princ (strcat "<script type=\"text/javascript\" src=\"" TmpScrHtmlEasyCut$ "tools01.js\"></script>\n")					Stream)				
			(princ "</head>\n" 																										Stream)
			(princ "<body>\n" 																										Stream)
			(princ "	<div class=\"wrapper\" align=\"center\">\n"																	Stream)
			(princ "		<div class=\"header clearfix\">\n"																		Stream)
			(princ "			<div class=\"print\" align=\"left\">\n"																Stream)
			(princ (strcat "	   " (Today) " " (Time) "\n")																		Stream)
			(princ "			<br> <br> \n"																						Stream)
			(princ "			<button onclick=\"myFunction()\">Stampa</button>\n"													Stream)
			(princ "			</div>\n"																							Stream)
			(princ "			<div class=\"logo\">\n"																				Stream)
			(princ (strcat "			<img src=\"file:///"   LibPathEasyCut$ "Logo.jpg\" alt=\"logo\">\n")						Stream)
			(princ "			</div>\n"																							Stream)
			(princ "		</div>\n"																								Stream)

			(setq conta 0)
			(setq LstDataFound (GetInfoCutSheetFound LstFoundSearch))
			(foreach Sheet LstFoundSearch
				(UpDateProgressBar)
				(setq EnameSheet 			(car Sheet))
				(setq DataSheet 			(GetDataSheetByEname EnameSheet)) 		 ; "293451914" "jkj" "2500" "5000" "10" "12.5" "981.25" "S355j0"
				;(setq DataCut   			(GetInfoCutSheet     EnameSheet))		 ; TotLgCut TotLgExtCut TotLgIntCut TotLgTriggerCut SpeedCut Timing TotSurface SheetSurface
				(setq DataCut   			(nth conta LstDataFound))				 ; TotLgCut TotLgExtCut TotLgIntCut TotLgTriggerCut SpeedCut Timing TotSurface SheetSurface
				(setq &JobNumber 			(strcat "J_" (nth 0 DataSheet)))
				(setq &SheetOrder 			(nth 1 DataSheet))
				(setq &SheetId 				(nth 0 DataSheet))
				(setq &SheetDim 			(strcat (LM:rtos (atoi (nth 2 DataSheet)) 2 0) "*" (LM:rtos (atoi (nth 3 DataSheet)) 2 0) "*" (nth 4 DataSheet))) 
				(setq &SheetMat 			(nth 7 DataSheet))
				(setq &SheetWidth 			(nth 2 DataSheet))
				(setq &SheetHeight 			(nth 3 DataSheet))
				(setq &SheetThikness		(nth 4 DataSheet))
				(setq &SheetSurface 		(nth 5 DataSheet))
				(setq &SheetWeight 			(nth 6 DataSheet))
				(setq &SheetSpeedCut		(LM:rtos (GetSpeedCutByThickness (nth 4 DataSheet)) 2 1))
				(setq &ShapeTotLgCut		(nth 1 DataCut))
				(setq $ShapeTimingCut		(MinSec (/ (atof &ShapeTotLgCut) (GetSpeedCutByThickness (nth 4 DataSheet)))))
				(setq &ShapeSurface			(nth 7 DataCut))
				(setq &ShapeWeight			(rtos (* (atof (nth 7 DataCut)) (atof (nth 4 DataSheet)) 7.85) 2 1))
				(setq &SheetScrapsSurface	(LM:rtos (- (atof (nth 8 DataCut)) (atof (nth 7 DataCut))) 2 1))
				(setq &SheetScrapsWeigth	(LM:rtos (* (- (atof (nth 8 DataCut)) (atof (nth 7 DataCut)))  (atof (nth 4 DataSheet)) 7.85) 2 1))
				(setq &SheetScrapsPercent   (LM:rtos (- 100.0 (* (/ (atof (nth 7 DataCut)) (atof (nth 8 DataCut))) 100.0)) 2 1))
				(princ "		<br>\n"					 																					Stream)
				(princ "		<div class=\"title\">\n" 																					Stream)
				(princ (strcat "			<b>Job &nbsp;" &JobNumber " </b>\n") 															Stream)
				(princ "		</div>\n" 																									Stream)		
				(princ "		<div class=\"infosheet\">\n"																				Stream)
				(princ "			<table border=\"1\" cellpadding=\"0\" cellspacing=\"0\" width=\"95%\">\n"								Stream)
				(princ "				<tr height=\"30px\" align=\"center\" bgcolor=\"#D8D8D8\">\n"										Stream)
				(princ (strcat "					<td width=\"25%\">Order " 	&SheetOrder 		"</td>\n")								Stream)
				(princ (strcat "					<td width=\"25%\">Id " 		&SheetId 			"</td>\n")								Stream)
				(princ (strcat "					<td width=\"25%\">Sheet " 	&SheetDim 			" mm</td>\n")							Stream)
				(princ "				</tr>\n"																							Stream)
				(princ "				<tr height=\"30px\" align=\"center\" bgcolor=\"#C0C0C0\">\n"										Stream)
				(princ (strcat "					<td width=\"25%\">Mat " 	&SheetMat 			"</td>\n")								Stream)
				(princ (strcat "					<td>Weigth sheet " 			&SheetWeight  		" kg</td>\n")							Stream)
				(princ (strcat "					<td>Weight shape " 			&ShapeWeight  		" kg</td>\n")							Stream)
				(princ "				</tr>\n"																							Stream)
				(princ "				<tr height=\"30px\" align=\"center\" bgcolor=\"#D8D8D8\">\n"										Stream)
				(princ (strcat "					<td>Sheet Area "   			&SheetSurface 		" mq</td>\n")							Stream)
				(princ (strcat "					<td>Shape Area "   			&ShapeSurface 		" mq</td>\n")							Stream)
				(princ (strcat "					<td>Scraps " 				&SheetScrapsPercent " %</td>\n")							Stream)
				(princ "				</tr>\n"																							Stream)
				(princ "				<tr height=\"30px\" align=\"center\" bgcolor=\"#C0C0C0\">\n"										Stream)
				(princ (strcat "					<td>Scraps " 				&SheetScrapsWeigth  " kg</td>\n")							Stream)
				(princ (strcat "					<td>Speed "  				&SheetSpeedCut 		" mm/min</td>\n")						Stream)
				(princ (strcat "					<td>Timing cut " 			$ShapeTimingCut 	"</td>\n")								Stream)
				(princ "				</tr>\n"																							Stream)
				(princ "			</table>\n"																								Stream)
				(princ "		</div>\n"																									Stream)
				(princ "		<br>\n"																										Stream)
				(princ "		<div class=\"title\">\n"																					Stream)
				(princ "			<b>Shape &nbsp; List</b>\n"																				Stream)
				(princ "		</div>\n"																									Stream)
				(princ "		<div class=\"infocatlist\">\n"																				Stream)
				(princ "			<table border=\"1\" cellpadding=\"0\" cellspacing=\"0\" width=\"95%\">\n"								Stream)
				(princ (strcat "				<tr height=\"30px\" align=\"center\" bgcolor= \"" (Swap Color1 Color2 1) "\">\n")			Stream)
				(princ "					<td><b>Itm</b></td>\n"																			Stream)
				(princ "					<td><b>Order</b></td>\n"																		Stream)
				(princ "					<td><b>Phase</b></td>\n"																		Stream)
				(princ "					<td><b>Mark</b></td>\n"																			Stream)
				(princ "					<td><b>Dimension</b></td>\n"																	Stream)
				(princ "					<td><b>Thik.</b></td>\n"																		Stream)
				(princ "					<td><b>Qta</b></td>\n"																			Stream)
				(princ "					<td><b>Tot Weight</b></td>\n"																	Stream)
				(princ "					<td><b>BarCode</b></td>\n"																		Stream)
				(princ "				</tr>\n"																							Stream)
				(setq Num 0)
				(setq TotQta 0)
				(setq TotWgt 0.0)
				(foreach Mark (cdr Sheet)
					(setq EnameRef   		(cadr Mark))
					(setq &ShapeOrder		(GetComShape   EnameRef))
					(setq &ShapePhase 	 	(GetPhaseShape EnameRef))
					(setq &ShapeName 		(GetNameShape  EnameRef))
					(setq &ShapeMat 		(GetMatShape   EnameRef))
					(setq &ShapeTk 			(GetTkShape    EnameRef))
					(setq &ShapeQta 		(rtos (- (length Mark) 1) 2 0))

					(setq Dim 	 			(GetDimensionDummy EnameRef))
					(setq Surface 	 		(/ (vla-get-area (vlax-ename->vla-object EnameRef)) 1000000.0))
					(setq Weight     		(* (* 7.85 Surface)   (atof (GetTkShape  EnameRef))))

					(setq &ShapeDim 		(strcat (rtos (car Dim) 2 1) "x" (rtos (cadr Dim) 2 1)))
					(setq &ShapeTotWeight  	(rtos (* Weight (atoi &ShapeQta)) 2 1))
					(setq &ShapeBarCode 	(GetBarCode EnameRef))
					;
					; Cut List +++++++++++++++++++++++++++++++++++++++++++++++++++++++++++++++++++++++++++++++++++++++++++++++++++++++++++++++++
					;
					(princ (strcat "				<tr height=\"30px\" align=\"center\" bgcolor= \"" (Swap Color1 Color2 Num) "\">\n")	Stream)
					(princ (strcat "					<td>" (NumToProg (1+ Num) 3) 		"</td>\n")										Stream)
					(princ (strcat "					<td>" &ShapeOrder				"</td>\n")										Stream)
					(princ (strcat "					<td>" &ShapePhase     			"</td>\n")										Stream)
					(princ (strcat "					<td>" &ShapeName      			"</td>\n")										Stream)
					(princ (strcat "					<td>" &ShapeDim       			"</td>\n")										Stream)
					(princ (strcat "					<td>" &ShapeTk        			"</td>\n")										Stream)
					(princ (strcat "					<td>" &ShapeQta       			"</td>\n")										Stream)
					(princ (strcat "					<td>" &ShapeTotWeight 			"</td>\n")										Stream)
					(setq IdRnd (Random_Str 9))
					(princ (strcat "					<td style=\"background-color:#ffffff\" align=\"center\">\n")					Stream)
					(princ (strcat "						<div id=\"" IdRnd "\" class=\"barcode\">\n")								Stream)
					(princ (strcat "							<script type=text/javascript>\n")										Stream)
					(princ (strcat "								generateBarcode(\"" IdRnd "\", \"" 	&ShapeBarCode "\", \"code128\", \"css\");\n")	Stream)
					(princ (strcat "							</script>\n")															Stream)
					(princ (strcat "						</div>\n")																	Stream)
					(princ (strcat "					</td>\n")																		Stream)
					(princ (strcat "				</tr>\n")																			Stream)
					(setq TotQta (+ TotQta (atoi &ShapeQta)))
					(setq TotWgt (+ TotWgt (atof &ShapeTotWeight)))
					(setq Num (1+ Num))
				)
				(princ (strcat "				<tr height=\"40px\" align=\"center\" bgcolor= \"" (Swap Color1 Color2 Num) "\">\n")		Stream)
				(princ (strcat "					<td>"  "</td>\n")																	Stream)
				(princ (strcat "					<td>"  "</td>\n")																	Stream)
				(princ (strcat "					<td>"  "</td>\n")																	Stream)
				(princ (strcat "					<td>"  "</td>\n")																	Stream)
				(princ (strcat "					<td>"  "</td>\n")																	Stream)
				(princ (strcat "					<td>" "Tot" "</td>\n")																Stream)
				(princ (strcat "					<td>" (LM:rtos TotQta 2 0) "</td>\n")												Stream)
				(princ (strcat "					<td>" (LM:rtos TotWgt 2 1) "</td>\n")												Stream)
				(princ (strcat "					<td>"  "</td>\n")																	Stream)
				(princ (strcat "				</tr>\n")																				Stream)
				(princ "			</table>\n"																							Stream)
				(princ "		</div>\n"																								Stream)
				(princ "		<br> <br>\n"																							Stream)
				(setq conta (1+ conta))
			)
			(ClearProgressBar)
			(princ "	</div>\n"																										Stream)
			(princ "</body>\n"																											Stream)
			(princ "</html>\n"																											Stream)		
			(close Stream)
		)
		(alert (strcat "ERRORE generazione Report [ReportFound]" NameReport))
	)
	NameReport
)
;
;
;
(defun ReportFoundShape (LstFoundSearch / Swap
										  Color1 Color2 NameReport Stream Mark Num TotQta TotWgt EnameBlock EnameShape LstCheck
										  &ShapeOrder &ShapePhase &ShapeName &ShapeQta &ShapeTk &ShapeMat WeightShape LengthShape WidthShape &ShapeDim &ShapeTotWeight &ShapeBarCode IdRnd) 

										  
										  
	;( ("Com|Phase|Name" EnameShape EnameShape) 
	;  ("Com|Phase|Name" EnameShape EnameShape) 
	;  ("Com|Phase|Name" EnameShape EnameShape))
	;)
	;
	(defun Swap (DatoA DatoB Indice / Rtn)
	
		(if (> (- (/ Indice 2.0) (fix (/ Indice 2.0))) 0)
			(setq Rtn DatoB)
			(setq Rtn DatoA)
		)
	)	
	;
	; Main
	;
	(setq Color1 "#DDEBF7")
	(setq Color2 "#BDD7EE")
	
	(setq NameReport (strcat HtmlStorageEasyCut$ ECFolderReport$ "FoundShape.html"))
	(setq Stream (open NameReport "w")) 
	(if Stream
		(progn
			(princ "<!DOCTYPE html PUBLIC \"-//W3C//DTD XHTML 1.0 Transitional//EN\" \"http://www.w3.org/TR/xhtml1/DTD/xhtml1-transitional.dtd\">\n" Stream)
			(princ "<html xmlns=\"http://www.w3.org/1999/xhtml\">\n" 																Stream)
			(princ "<head>\n" 																										Stream)
			(princ "<meta http-equiv=\"Content-Type\" content=\"text/html; charset=iso-8859-1\" />\n" 								Stream)
			(princ (strcat "<link rel=\"stylesheet\" type=\"text/css\" href=\"" TmpScrHtmlEasyCut$ "normalize.css\" />\n")			Stream)
			(princ "<title>Untitled Document</title>\n" 																			Stream)
			(princ "<style type=\"text/css\">\n"																					Stream)
			(princ ".wrapper          {width:100%;margin-left:auto;margin-right:auto;font-family:Arial;}\n"							Stream)
			(princ ".print            {font-size:12px; float: left;}\n"																Stream)
			(princ ".title            {font-size:18px}\n"																			Stream)
			(princ ".infocatlist      {margin-top:5px;}\n"																			Stream)
			(princ ".td               {font-size: 9pt;}\n"																			Stream)
			(princ ".barcode          {margin-top: 5px;}\n"																			Stream)
			(princ "@page             {size: 210mm 297mm; margin: 5mm;}\n"															Stream)
			(princ "tr                {page-break-inside: avoid;}\n"																Stream)
			(princ ".header		      {}\n"																							Stream)
			(princ ".logo	          {float: right; height: 45px;}\n"																Stream)
			(princ ".logo img	      {height: 45px; display: inline-block;}\n"														Stream)
			(princ ".clearfix:after   {visibility: hidden; display: block; font-size: 0; content: \" \"; clear: both; height: 0;}\n" Stream)
			(princ "* html .clearfix  {zoom: 1;} /* IE6 */\n"																		Stream)
			(princ "*:first-child+html .clearfix {zoom: 1;} /* IE7 */\n"															Stream)
			(princ "</style>\n"																										Stream)
			(princ (strcat "<script type=\"text/javascript\" src=\"" TmpScrHtmlEasyCut$ "jquery-1.3.2.min.js\"></script>\n")		Stream)
			(princ (strcat "<script type=\"text/javascript\" src=\"" TmpScrHtmlEasyCut$ "jquery-barcode-2.0.2.min.js\"></script>\n")Stream)				
			(princ (strcat "<script type=\"text/javascript\" src=\"" TmpScrHtmlEasyCut$ "tools01.js\"></script>\n")					Stream)				
			(princ "</head>\n" 																										Stream)
			(princ "<body>\n" 																										Stream)
			(princ "	<div class=\"wrapper\" align=\"center\">\n"																	Stream)
			(princ "		<div class=\"header clearfix\">\n"																		Stream)
			(princ "			<div class=\"print\" align=\"left\">\n"																Stream)
			(princ (strcat "	   " (Today) " " (Time) "\n")																		Stream)
			(princ "			<br> <br> \n"																						Stream)
			(princ "			<button onclick=\"myFunction()\">Stampa</button>\n"													Stream)
			(princ "			</div>\n"																							Stream)
			(princ "			<div class=\"logo\">\n"																				Stream)
			(princ (strcat "			<img src=\"file:///"   LibPathEasyCut$ "Logo.jpg\" alt=\"logo\">\n")						Stream)
			(princ "			</div>\n"																							Stream)
			(princ "		</div>\n"																								Stream)
			(princ "		<br>\n"					 																				Stream)
			(princ "		<div class=\"title\">\n"																				Stream)
			(princ "			<b>Shape &nbsp; List</b>\n"																			Stream)
			(princ "		</div>\n"																								Stream)
			(princ "		<div class=\"infocatlist\">\n"																			Stream)
			(princ "			<table border=\"1\" cellpadding=\"0\" cellspacing=\"0\" width=\"95%\">\n"							Stream)
			(princ (strcat "				<tr height=\"30px\" align=\"center\" bgcolor= \"" (Swap Color1 Color2 1) "\">\n")		Stream)
			(princ "					<td><b>Itm</b></td>\n"																		Stream)
			(princ "					<td><b>Order</b></td>\n"																	Stream)
			(princ "					<td><b>Phase</b></td>\n"																	Stream)
			(princ "					<td><b>Mark</b></td>\n"																		Stream)
			(princ "					<td><b>Dimension</b></td>\n"																Stream)
			(princ "					<td><b>Thik.</b></td>\n"																	Stream)
			(princ "					<td><b>Qta</b></td>\n"																		Stream)
			(princ "					<td><b>Tot Weight</b></td>\n"																Stream)
			(princ "					<td><b>BarCode</b></td>\n"																	Stream)
			(princ "				</tr>\n"																						Stream)
			(setq LstCheck (GetLstIdAndEnameShape))
			(setq TotQta 0)
			(setq TotWgt 0.0)
			(setq Num 0)
			(StartProgressBar "Report" (length LstFoundSearch))
			
			(foreach Mark LstFoundSearch
				(UpDateProgressBar)
				
				(foreach EnameBlock (cdr Mark)

					(setq EnameShape (cadr (assoc (LM:vl-getattributevalue (vlax-ename->vla-object EnameBlock) "IDSHAPE") LstCheck)))

					(setq &ShapeOrder (LM:vl-getattributevalue (vlax-ename->vla-object EnameBlock) "ORDERSHAPE")) 		; nome commessa
					(setq &ShapePhase (LM:vl-getattributevalue (vlax-ename->vla-object EnameBlock) "PHASESHAPE"))		; nome fase
					(setq &ShapeName  (LM:vl-getattributevalue (vlax-ename->vla-object EnameBlock) "MKSHAPE"))			; nome pezzo
					(setq &ShapeQta   (LM:vl-getattributevalue (vlax-ename->vla-object EnameBlock) "QTASHAPE"))			; quantità
					(setq &ShapeTk    (LM:vl-getattributevalue (vlax-ename->vla-object EnameBlock) "TKSHAPE"))			; spessore
					(setq &ShapeMat   (LM:vl-getattributevalue (vlax-ename->vla-object EnameBlock) "MATSHAPE"))			; materiale

					(setq WeightShape (LM:vl-getattributevalue (vlax-ename->vla-object EnameBlock) "WEIGTHSHAPE"))		; peso
					(setq LengthShape (LM:vl-getattributevalue (vlax-ename->vla-object EnameBlock) "LENGTHSHAPE"))		; lunghezza
					(setq WidthShape  (LM:vl-getattributevalue (vlax-ename->vla-object EnameBlock) "HEIGHTSHAPE"))		; larghezza

					(setq &ShapeDim    		(strcat (rtos (atof LengthShape) 2 1) "x" (rtos (atof WidthShape) 2 1)))
					(setq &ShapeTotWeight  	(rtos (* (atof WeightShape) (atoi &ShapeQta)) 2 1))
					(setq &ShapeBarCode 	(GetBarCode EnameShape))
					;
					; Cut List +++++++++++++++++++++++++++++++++++++++++++++++++++++++++++++++++++++++++++++++++++++++++++++++++++++++++++++++++
					;
					(princ (strcat "				<tr height=\"30px\" align=\"center\" bgcolor= \"" (Swap Color1 Color2 Num) "\">\n")	Stream)
					(princ (strcat "					<td>" (NumToProg (1+ Num) 3) 		"</td>\n")										Stream)
					(princ (strcat "					<td>" &ShapeOrder				"</td>\n")										Stream)
					(princ (strcat "					<td>" &ShapePhase     			"</td>\n")										Stream)
					(princ (strcat "					<td>" &ShapeName      			"</td>\n")										Stream)
					(princ (strcat "					<td>" &ShapeDim       			"</td>\n")										Stream)
					(princ (strcat "					<td>" &ShapeTk        			"</td>\n")										Stream)
					(princ (strcat "					<td>" &ShapeQta       			"</td>\n")										Stream)
					(princ (strcat "					<td>" &ShapeTotWeight 			"</td>\n")										Stream)
					(setq IdRnd (Random_Str 9))
					(princ (strcat "					<td style=\"background-color:#ffffff\" align=\"center\">\n")					Stream)
					(princ (strcat "						<div id=\"" IdRnd "\" class=\"barcode\">\n")								Stream)
					(princ (strcat "							<script type=text/javascript>\n")										Stream)
					(princ (strcat "								generateBarcode(\"" IdRnd "\", \"" 	&ShapeBarCode "\", \"code128\", \"css\");\n")	Stream)
					(princ (strcat "							</script>\n")															Stream)
					(princ (strcat "						</div>\n")																	Stream)
					(princ (strcat "					</td>\n")																		Stream)
					(princ (strcat "				</tr>\n")																			Stream)
					(setq TotQta (+ TotQta (atoi &ShapeQta)))
					(setq TotWgt (+ TotWgt (atof &ShapeTotWeight)))
					(setq Num (1+ Num))
				)
			)
			(princ (strcat "				<tr height=\"40px\" align=\"center\" bgcolor= \"" (Swap Color1 Color2 Num) "\">\n")			Stream)
			(princ (strcat "					<td>"  "</td>\n")																		Stream)
			(princ (strcat "					<td>"  "</td>\n")																		Stream)
			(princ (strcat "					<td>"  "</td>\n")																		Stream)
			(princ (strcat "					<td>"  "</td>\n")																		Stream)
			(princ (strcat "					<td>"  "</td>\n")																		Stream)
			(princ (strcat "					<td>" "Tot" "</td>\n")																	Stream)
			(princ (strcat "					<td>" (LM:rtos TotQta 2 0) "</td>\n")													Stream)
			(princ (strcat "					<td>" (LM:rtos TotWgt 2 1) "</td>\n")													Stream)
			(princ (strcat "					<td>"  "</td>\n")																		Stream)
			(princ (strcat "				</tr>\n")																					Stream)
			(princ "			</table>\n"																								Stream)
			(princ "		</div>\n"																									Stream)
			(princ "		<br> <br>\n"																								Stream)
			(ClearProgressBar)
			(princ "	</div>\n"																										Stream)
			(princ "</body>\n"																											Stream)
			(princ "</html>\n"																											Stream)		
			(close Stream)
		)
		(alert (strcat "ERRORE generazione Report [ReportFoundShape]" NameReport))
	)
	NameReport
)
;
;
;
(defun ReportCheckNesting (LstMarKShape LstMarKSheet / Swap
													   Color1 Color2 Num NameReport Stream
													   itm Data LstData OrderShape PhaseShape NameShape TkShape QtaShape CheckQtaShape Diff)
	
	; LstMarKShape
	; ( ("123|456|789" EnameRef 10) ("123|456|111" EnameRef 8) ...... )
	
	; LstMarKSheet
	; ( ("123|456|789" EnameRef 10) ("123|456|111" EnameRef 8) ...... )
	
	(defun Swap (DatoA DatoB Indice / Rtn)
	
		(if (> (- (/ Indice 2.0) (fix (/ Indice 2.0))) 0)
			(setq Rtn DatoB)
			(setq Rtn DatoA)
		)
	)	
	;
	; Main
	; 
	(setq Color1 "#DDEBF7")
	(setq Color2 "#BDD7EE")
	

	(if (and LstMarKShape LstMarKSheet)
		(progn
			(setq NameReport (strcat HtmlStorageEasyCut$ ECFolderReport$ "NestingCheck.html"))
			(setq Stream (open NameReport "w")) 
			(if Stream
				(progn
					(foreach itm LstMarKShape
						(setq OrderShape (car   (splitxt (car itm) "|")))
						(setq PhaseShape (cadr  (splitxt (car itm) "|")))
						(setq NameShape  (caddr (splitxt (car itm) "|")))
						(setq QtaShape   (rtos  (caddr itm) 2 0))
						(setq TkShape    (GetTkShape (cadr itm)))
						
						(if (setq Data (assoc (car itm) LstMarKSheet))
							(setq CheckQtaShape (rtos (caddr Data) 2 0))
							(setq CheckQtaShape "0")
						)
						(setq LstData (append LstData (list (list OrderShape PhaseShape NameShape QtaShape TkShape CheckQtaShape))))
					)
					(setq LstData (SortTable LstData '(1 2 3 0 0 0) "<"))

					(princ "<!DOCTYPE html PUBLIC \"-//W3C//DTD XHTML 1.0 Transitional//EN\" \"http://www.w3.org/TR/xhtml1/DTD/xhtml1-transitional.dtd\">\n" Stream)
					(princ "<html xmlns=\"http://www.w3.org/1999/xhtml\">\n" 																Stream)
					(princ "<head>\n" 																										Stream)
					(princ "<meta http-equiv=\"Content-Type\" content=\"text/html; charset=iso-8859-1\" />\n" 								Stream)
					(princ (strcat "<link rel=\"stylesheet\" type=\"text/css\" href=\"" TmpScrHtmlEasyCut$ "normalize.css\" />\n")			Stream)
					(princ "<title>Untitled Document</title>\n" 																			Stream)
					(princ "<style type=\"text/css\">\n"																					Stream)
					(princ ".wrapper          {width:100%;margin-left:auto;margin-right:auto;font-family:Arial;}\n"							Stream)
					(princ ".print            {font-size:12px; float: left;}\n"																Stream)
					(princ ".title            {font-size:18px}\n"																			Stream)
					(princ ".infocatlist      {margin-top:5px;}\n"																			Stream)
					(princ ".td               {font-size: 9pt;}\n"																			Stream)
					(princ ".barcode          {margin-top: 5px;}\n"																			Stream)
					(princ "@page             {size: 210mm 297mm; margin: 5mm;}\n"															Stream)
					(princ "tr                {page-break-inside: avoid;}\n"																Stream)
					(princ ".header		      {}\n"																							Stream)
					(princ ".logo	          {float: right; height: 45px;}\n"																Stream)
					(princ ".logo img	      {height: 45px; display: inline-block;}\n"														Stream)
					(princ ".clearfix:after   {visibility: hidden; display: block; font-size: 0; content: \" \"; clear: both; height: 0;}\n" Stream)
					(princ "* html .clearfix  {zoom: 1;} /* IE6 */\n"																		Stream)
					(princ "*:first-child+html .clearfix {zoom: 1;} /* IE7 */\n"															Stream)
					(princ "</style>\n"																										Stream)
					(princ (strcat "<script type=\"text/javascript\" src=\"" TmpScrHtmlEasyCut$ "jquery-1.3.2.min.js\"></script>\n")		Stream)
					(princ (strcat "<script type=\"text/javascript\" src=\"" TmpScrHtmlEasyCut$ "jquery-barcode-2.0.2.min.js\"></script>\n")Stream)				
					(princ (strcat "<script type=\"text/javascript\" src=\"" TmpScrHtmlEasyCut$ "tools01.js\"></script>\n")					Stream)				
					(princ (strcat "<script type=\"text/javascript\" src=\"" TmpScrHtmlEasyCut$ "acadbridge.js\"></script>\n")				Stream)					
					(princ "</head>\n" 																										Stream)
					(princ "<body>\n" 																										Stream)
					(princ "	<div class=\"wrapper\" align=\"center\">\n"																	Stream)
					(princ "		<div class=\"header clearfix\">\n"																		Stream)
					(princ "			<div class=\"print\" align=\"left\">\n"																Stream)
					(princ (strcat "	   " (Today) " " (Time) "\n")																		Stream)
					(princ "			<br> <br> \n"																						Stream)
					(princ "			<button onclick=\"myFunction()\">Stampa</button>\n"													Stream)
					(princ "			</div>\n"																							Stream)
					(princ "			<div class=\"logo\">\n"																				Stream)
					(princ (strcat "			<img src=\"file:///"   LibPathEasyCut$ "Logo.jpg\" alt=\"logo\">\n")						Stream)
					(princ "			</div>\n"																							Stream)
					(princ "		</div>\n"																								Stream)


					(princ "		<br>\n"					 																				Stream)
					(princ "		<div class=\"title\">\n"																				Stream)
					(princ "			<b>Shape &nbsp; Nested &nbsp; List</b>\n"															Stream)
					(princ "		</div>\n"																								Stream)
					(princ "		<div class=\"infocatlist\">\n"																			Stream)
					(princ "			<table border=\"1\" cellpadding=\"0\" cellspacing=\"0\" width=\"95%\">\n"							Stream)
					(princ (strcat "				<tr height=\"30px\" align=\"center\" bgcolor= \"" (Swap Color1 Color2 1) "\">\n")		Stream)
					(princ "					<td width=\"10%\"><b>Itm</b></td>\n"														Stream)
					(princ "					<td width=\"15%\"><b>Order</b></td>\n"														Stream)
					(princ "					<td width=\"15%\"><b>Phase</b></td>\n"														Stream)
					(princ "					<td width=\"15%\"><b>Mark</b></td>\n"														Stream)
					(princ "					<td width=\"11%\"><b>Thick</b></td>\n"														Stream)
					(princ "					<td	width=\"12%\"><b>Qty Shape</b></td>\n"													Stream)
					(princ "					<td width=\"12%\"><b>Qty Nested</b></td>\n"													Stream)
					(princ "					<td width=\"10%\"><b>Diff.</b></td>\n"														Stream)
					(princ "				</tr>\n"																						Stream)

					
					(setq Num 0)
					(StartProgressBar "Report" (length LstNameShape))
					(foreach itm LstData
						;     0           1         2        3        4         5 
						; OrderShape PhaseShape NameShape QtaShape TkShape CheckQtaShape
						(UpDateProgressBar)
						(princ (strcat "				<tr height=\"30px\" align=\"center\" bgcolor= \"" (Swap Color1 Color2 Num) "\">\n")	Stream)
						(princ (strcat "					<td>" (NumToProg (1+ Num) 3) 		"</td>\n")									Stream)
						(princ (strcat "					<td>" (nth 0 itm)					"</td>\n")									Stream)
						(princ (strcat "					<td>" (nth 1 itm) 					"</td>\n")									Stream)
						(princ (strcat "					<td>" (nth 2 itm)    				"</td>\n")									Stream)
						(princ (strcat "					<td>" (nth 4 itm)    	    		"</td>\n")									Stream)
						(if (= (atoi (nth 3 itm)) 0)
							(princ (strcat "					<td bgcolor=\"red\">" (nth 3 itm)   "</td>\n")								Stream)
							(princ (strcat "					<td>" (nth 3 itm)       			"</td>\n")								Stream)
						)

						(princ (strcat "					<td>" (nth 5 itm)    				"</td>\n")									Stream)
						(cond
							((< (setq Diff  (- (atoi (nth 5 itm)) (atoi (nth 3 itm)))) 0) 
								(princ (strcat "					<td bgcolor=\"red\">" (rtos Diff 2 0)   "</td>\n")						Stream)
							)
							((> (setq Diff  (- (atoi (nth 5 itm)) (atoi (nth 3 itm)))) 0)
								(princ (strcat "					<td bgcolor=\"yellow\">" (rtos Diff 2 0)  "</td>\n")					Stream)
							)
							(t
								(princ (strcat "					<td bgcolor=\"green\">" (rtos Diff 2 0)   "</td>\n")					Stream)
							)
						)
						(princ (strcat "				</tr>\n")																			Stream)
						(setq Num (1+ Num))
					)
					(princ "			</table>\n"																							Stream)
					(princ "		</div>\n"																								Stream)
					(princ "		<br> <br>\n"																							Stream)
					(ClearProgressBar)
					(princ "	</div>\n"																									Stream)
					(princ "</body>\n"																										Stream)
					(princ "</html>\n"																										Stream)		
					(close Stream)
				)
				(alert (strcat "ERRORE generazione Report [ReportCheckNesting]" NameReport))
			)
		)
	)
	NameReport
)
;
;
;
(defun ReportDeductNesting (LstMarKShape  / Swap
											Color1 Color2 Num NameReport Stream
											itm Data LstData)
	
	; LstMarKShape
	;(	("824663856" "C000H" "2" "1086" "6" "40" "820" "520" "S275JR" "30/11/2020" "Antioraria") 
	;	("854512241" "C000H" "2" "1087" "8" "40" "720" "520" "S275JR" "30/11/2020" "Antioraria"))

	(defun Swap (DatoA DatoB Indice / Rtn)
	
		(if (> (- (/ Indice 2.0) (fix (/ Indice 2.0))) 0)
			(setq Rtn DatoB)
			(setq Rtn DatoA)
		)
	)	
	;
	; Main
	; 
	(setq Color1 "#DDEBF7")
	(setq Color2 "#BDD7EE")
	

	(if LstMarKShape
		(progn
			(setq NameReport (strcat HtmlStorageEasyCut$ ECFolderReport$ "NestingDeduct.html"))
			(setq Stream (open NameReport "w")) 
			(if Stream
				(progn
					(foreach itm LstMarKShape
						(setq LstData (append LstData (list (list 	(nth 1 itm) ;OrderShape 
																	(nth 2 itm) ;PhaseShape
																	(nth 3 itm) ;NameShape
																	(nth 4 itm) ;QtaShape
																	(nth 5 itm) ;ThickShape
																	(nth 6 itm) ;LengShape
																	(nth 7 itm) ;WidthShape
																	(nth 8 itm) ;MatShape
															))))
					)
					(setq LstData (SortTable LstData '(1 2 3 0 0 0) "<"))
					(princ "<!DOCTYPE html PUBLIC \"-//W3C//DTD XHTML 1.0 Transitional//EN\" \"http://www.w3.org/TR/xhtml1/DTD/xhtml1-transitional.dtd\">\n" Stream)
					(princ "<html xmlns=\"http://www.w3.org/1999/xhtml\">\n" 																Stream)
					(princ "<head>\n" 																										Stream)
					(princ "<meta http-equiv=\"Content-Type\" content=\"text/html; charset=iso-8859-1\" />\n" 								Stream)
					(princ (strcat "<link rel=\"stylesheet\" type=\"text/css\" href=\"" TmpScrHtmlEasyCut$ "normalize.css\" />\n")			Stream)
					(princ "<title>Untitled Document</title>\n" 																			Stream)
					(princ "<style type=\"text/css\">\n"																					Stream)
					(princ ".wrapper          {width:100%;margin-left:auto;margin-right:auto;font-family:Arial;}\n"							Stream)
					(princ ".print            {font-size:12px; float: left;}\n"																Stream)
					(princ ".title            {font-size:18px}\n"																			Stream)
					(princ ".infocatlist      {margin-top:5px;}\n"																			Stream)
					(princ ".td               {font-size: 9pt;}\n"																			Stream)
					(princ ".barcode          {margin-top: 5px;}\n"																			Stream)
					(princ "@page             {size: 210mm 297mm; margin: 5mm;}\n"															Stream)
					(princ "tr                {page-break-inside: avoid;}\n"																Stream)
					(princ ".header		      {}\n"																							Stream)
					(princ ".logo	          {float: right; height: 45px;}\n"																Stream)
					(princ ".logo img	      {height: 45px; display: inline-block;}\n"														Stream)
					(princ ".clearfix:after   {visibility: hidden; display: block; font-size: 0; content: \" \"; clear: both; height: 0;}\n" Stream)
					(princ "* html .clearfix  {zoom: 1;} /* IE6 */\n"																		Stream)
					(princ "*:first-child+html .clearfix {zoom: 1;} /* IE7 */\n"															Stream)
					(princ "</style>\n"																										Stream)
					(princ (strcat "<script type=\"text/javascript\" src=\"" TmpScrHtmlEasyCut$ "jquery-1.3.2.min.js\"></script>\n")		Stream)
					(princ (strcat "<script type=\"text/javascript\" src=\"" TmpScrHtmlEasyCut$ "jquery-barcode-2.0.2.min.js\"></script>\n")Stream)				
					(princ (strcat "<script type=\"text/javascript\" src=\"" TmpScrHtmlEasyCut$ "tools01.js\"></script>\n")					Stream)
					(princ (strcat "<script type=\"text/javascript\" src=\"" TmpScrHtmlEasyCut$ "acadbridge.js\"></script>\n")				Stream)					
					(princ "</head>\n" 																										Stream)
					(princ "<body>\n" 																										Stream)
					(princ "	<div class=\"wrapper\" align=\"center\">\n"																	Stream)
					(princ "		<div class=\"header clearfix\">\n"																		Stream)
					(princ "			<div class=\"print\" align=\"left\">\n"																Stream)
					(princ (strcat "	   " (Today) " " (Time) "\n")																		Stream)
					(princ "			<br> <br> \n"																						Stream)
					(princ "			<button onclick=\"myFunction()\">Stampa</button>\n"													Stream)
					(princ "			</div>\n"																							Stream)
					(princ "			<div class=\"logo\">\n"																				Stream)
					(princ (strcat "			<img src=\"file:///"   LibPathEasyCut$ "Logo.jpg\" alt=\"logo\">\n")						Stream)
					(princ "			</div>\n"																							Stream)
					(princ "		</div>\n"																								Stream)
					(princ "		<br>\n"					 																				Stream)
					(princ "		<div class=\"title\">\n"																				Stream)
					(princ "			<b>Shape &nbsp; Not &nbsp; Nested &nbsp; List</b>\n"												Stream)
					(princ "		</div>\n"																								Stream)
					(princ "		<div class=\"infocatlist\">\n"																			Stream)
					(princ "			<table border=\"1\" cellpadding=\"0\" cellspacing=\"0\" width=\"95%\">\n"							Stream)
					(princ (strcat "				<tr height=\"30px\" align=\"center\" bgcolor= \"" (Swap Color1 Color2 1) "\">\n")		Stream)
					(princ "					<td width=\"8%\"><b>Itm</b></td>\n"															Stream)
					(princ "					<td width=\"14%\"><b>Order</b></td>\n"														Stream)
					(princ "					<td width=\"10%\"><b>Phase</b></td>\n"														Stream)
					(princ "					<td width=\"14%\"><b>Mark</b></td>\n"														Stream)
					(princ "					<td	width=\"8%\"><b>Qty</b></td>\n"															Stream)
					(princ "					<td	width=\"8%\"><b>Thick.</b></td>\n"														Stream)
					(princ "					<td	width=\"14%\"><b>Length</b></td>\n"														Stream)
					(princ "					<td width=\"14%\"><b>Width</b></td>\n"														Stream)
					(princ "					<td width=\"10%\"><b>Mat</b></td>\n"														Stream)
					(princ "				</tr>\n"																						Stream)
					(setq Num 0)
					(StartProgressBar "Report" (length LstNameShape))
					(foreach itm LstData
						;OrderShape PhaseShape NameShape QtaShape ThickShape LengShape WidthShape MatShape
						(UpDateProgressBar)
						(princ (strcat "				<tr height=\"30px\" align=\"center\" bgcolor= \"" (Swap Color1 Color2 Num) "\">\n")	Stream)
						(princ (strcat "					<td>" (NumToProg (1+ Num) 3) 		"</td>\n")									Stream)
						(princ (strcat "					<td>" (nth 0 itm)					"</td>\n")									Stream)
						(princ (strcat "					<td>" (nth 1 itm) 					"</td>\n")									Stream)
						(princ (strcat "					<td>" (nth 2 itm)    				"</td>\n")									Stream)
						(princ (strcat "					<td>" (nth 3 itm)       			"</td>\n")									Stream)
						(princ (strcat "					<td>" (nth 4 itm)      				"</td>\n")									Stream)
						(princ (strcat "					<td>" (nth 5 itm)       			"</td>\n")									Stream)
						(princ (strcat "					<td>" (nth 6 itm)      				"</td>\n")									Stream)
						(princ (strcat "					<td>" (nth 7 itm)       			"</td>\n")									Stream)
						(princ (strcat "				</tr>\n")																			Stream)
						(setq Num (1+ Num))
					)
					(princ "			</table>\n"																							Stream)
					(princ "		</div>\n"																								Stream)
					(princ "		<br> <br>\n"																							Stream)
					(ClearProgressBar)
					(princ "	</div>\n"																									Stream)
					(princ "</body>\n"																										Stream)
					(princ "</html>\n"																										Stream)		
					(close Stream)
				)
				(alert (strcat "ERRORE generazione Report [ReportDeductNesting]" NameReport))
			)
		)
	)
	NameReport
)
;
;
;
