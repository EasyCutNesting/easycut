;;; ============================================================
;;; TOCCA.LSP - Trasla una polilinea (A) fino al contatto con la
;;;             prima di una lista di polilinee (B1, B2, ...),
;;;             in una direzione data.
;;;
;;; Prima del calcolo vero e proprio, la lista di B viene
;;; filtrata: se un B piu' vicino ad A, lungo la direzione di
;;; moto, "fa ombra" (copre interamente) a un B piu' lontano,
;;; quest'ultimo viene escluso dal controllo, perche' A
;;; incontrerebbe comunque prima l'altro. L'ombra e' calcolata
;;; in modo esatto (non solo min/max), quindi funziona anche se
;;; i B sono poligoni concavi con "vuoti" nella proiezione.
;;;
;;; Vale per poligoni (A e B) concavi o convessi, con lati
;;; comunque inclinati. Le polilinee con archi (bulge) non sono
;;; supportate e vengono scartate in selezione.
;;;
;;; Comando: TOCCA
;;;   1. seleziona il poligono da spostare (A)
;;;   2. seleziona uno o piu' poligoni fissi (B), INVIO per finire
;;;   3. scegli la direzione: X+ X- Y+ Y- oppure Angolo
;;; ============================================================
(setq *tc-eps* 1e-9)
;; ---- Prodotto vettoriale 2D --------------------------------
(defun tc:cross (u v)
	(- (* (car u) (cadr v)) (* (cadr u) (car v)))
)
;; ---- Prodotto scalare 2D (proiezione di un punto su un asse) -
(defun tc:project (pt v)
	(+ (* (car pt) (car v)) (* (cadr pt) (cadr v)))
)
;; ---- Vertici 2D di una LWPOLYLINE --------------------------
(defun tc:verts (en / pts)
	(foreach g (entget en)
		(if (= (car g) 10)
			(setq pts (cons (list (cadr g) (caddr g)) pts))
		)
	)
	(reverse pts)
)
;; ---- Controllo: solo segmenti rettilinei -------------------
(defun tc:has-bulge (en)
	(vl-some
		'(lambda (g) (and (= (car g) 42) (> (abs (cdr g)) 1e-12)))
		(entget en)
	)
)
;; ---- Lati del poligono (sempre chiuso): lista di (q1 q2) ---
(defun tc:edges (pts / res n i)
	(setq n (length pts) i 0)
	(repeat n
		(setq res (cons (list (nth i pts) (nth (rem (1+ i) n) pts)) res))
		(setq i (1+ i))
	)
	(reverse res)
)
;; ---- Orientamento di un poligono dai suoi lati:
;;      +1.0 antiorario, -1.0 orario ---------------------------
(defun tc:orient (edges / a)
	(setq a 0.0)
	(foreach ed edges
		(setq a (+ a (tc:cross (car ed) (cadr ed))))
	)
	(if (>= a 0.0) 1.0 -1.0)
)
(defun tc:ray (pts edges d / best q1 q2 e den w tt s sgn)
	(setq sgn (tc:orient edges))
	(foreach ed edges
		(setq q1  (car ed)
			  q2  (cadr ed)
			  e   (list (- (car q2) (car q1)) (- (cadr q2) (cadr q1)))
			  den (tc:cross d e)
		)
		(if (> (abs den) *tc-eps*)
			(foreach p pts
				(setq w  (list (- (car q1) (car p)) (- (cadr q1) (cadr p)))
					  tt (/ (tc:cross w e) den)
					  s  (/ (tc:cross w d) den)
				)
				(if (and (>= tt (- *tc-eps*))
						 (>= s  (- *tc-eps*))
						 (<= s  (+ 1.0 *tc-eps*))
						 ;; contatto gia' in atto (tt ~ 0): vale solo se
						 ;; la direzione d entra nell'interno del poligono
						 (or (> tt *tc-eps*)
							 (> (* sgn (tc:cross e d)) *tc-eps*)
						 )
					)
					(setq tt   (max tt 0.0)
						  best (if best (min best tt) tt)
					)
				)
			)
		)
	)
	best
)
;; ---- Distanza di traslazione di A verso d fino al contatto
;;      con un B, dati vertici/lati gia' calcolati di entrambi.
;;      Ritorna nil se non c'e' mai contatto in quella direzione.
(defun tc:distance2 (va edges-a vb edges-b d / r1 r2 dneg)
	(setq dneg 	 (list (- (car d)) (- (cadr d)))
			r1   (tc:ray va edges-b d)      ; vertici A -> lati B
			r2   (tc:ray vb edges-a dneg)   ; vertici B -> lati A
	)
	(cond
		((and r1 r2) (min r1 r2))
		(r1 r1)
		(r2 r2)
	)
)
;; ---- Minima proiezione dei vertici su una direzione --------
(defun tc:min-projection (verts dir / m v)
	(foreach pt verts
		(setq v (tc:project pt dir))
		(if (or (null m) (< v m)) (setq m v))
	)
	m
)
;; ---- Un segmento (q1 q2) attraversa la retta infinita che
;;      passa per p0 con direzione d? (solo per il test di
;;      presenza di materiale, non calcola la distanza). ------
(defun tc:edge-crosses-line (p0 d q1 q2 / e den w s)
	(setq e   (list (- (car q2) (car q1)) (- (cadr q2) (cadr q1)))
		  den (tc:cross d e)
	)
	(if (> (abs den) *tc-eps*)
		(progn
			(setq w (list (- (car q1) (car p0)) (- (cadr q1) (cadr p0))))
			(setq s (/ (tc:cross w d) den))
			(if (and (>= s (- *tc-eps*)) (<= s (+ 1.0 *tc-eps*))) T)
		)
	)
)
;; ---- Punto sulla retta perpendicolare p, a distanza pm
;;      dall'origine lungo l'asse p (d-coordinata nulla). ------
(defun tc:point-on-p (p pm)
	(list (* (car p) pm) (* (cadr p) pm))
)
;; ---- Elimina duplicati da una lista di numeri GIA' ordinata -
(defun tc:dedupe (sorted / out)
	(foreach v sorted
		(if (or (null out) (> (- v (car out)) *tc-eps*))
			(setq out (cons v out))
		)
	)
	(reverse out)
)
;; ---- "Ombra reale" di un poligono lungo l'asse perpendicolare
;;      p, rispetto alla direzione di moto d: lista di
;;      intervalli (a . b) dove esiste davvero del contorno,
;;      con eventuali buchi se il poligono e' concavo. ---------
(defun tc:shadow-intervals (verts edges d p / breaks sorted n i a b pm p0 material ivs)
	(setq breaks nil)
	(foreach pt verts 
		(setq breaks (cons (tc:project pt p) breaks))
	)
	(setq sorted (tc:dedupe (vl-sort breaks '<)))
	(setq n (length sorted) i 0 ivs nil)
	(while (< i (1- n))
		(setq a (nth i sorted) b (nth (1+ i) sorted))
		(if (> (- b a) *tc-eps*)
			(progn
				(setq pm (/ (+ a b) 2.0)
					  p0 (tc:point-on-p p pm)
					  material nil
				)
				(foreach ed edges
					(if (and (not material)
						(tc:edge-crosses-line p0 d (car ed) (cadr ed)))
						(setq material T)
					)
				)
				(if material (setq ivs (cons (cons a b) ivs)))
			)
		)
		(setq i (1+ i))
	)
	(tc:merge-intervals (reverse ivs))
)
;; ---- Unisce una lista di intervalli (a . b) sovrapposti o
;;      adiacenti in una lista minima ordinata e disgiunta. ----
(defun tc:merge-intervals (ivs / sorted out last)
	(setq sorted (vl-sort ivs '(lambda (x y) (< (car x) (car y)))))
	(foreach iv sorted
		(if (and last (<= (car iv) (+ (cdr last) *tc-eps*)))
			(setq last (cons (car last) (max (cdr last) (cdr iv))))
			(progn
				(if last (setq out (cons last out)))
				(setq last iv)
			)
		)
	)
	(if last 
		(setq out (cons last out))
	)
	(reverse out)
)
;; ---- Un intervallo (a . b) e' interamente contenuto nella
;;      lista 'covering' (gia' unita/ordinata)? ----------------
(defun tc:interval-covered-p (iv covering)
	(vl-some
		'(lambda (c)
			(and (<= (car c) (+ (car iv) *tc-eps*))
				 (>= (cdr c) (- (cdr iv) *tc-eps*))
			)
		)
		covering
	)
)
;; ---- Tutti gli intervalli di 'shadow' sono coperti da
;;      'covering'? Lista vuota => non coperto (si mantiene). --
(defun tc:shadow-covered-p (shadow covering)
	(and shadow (vl-every '(lambda (iv) (tc:interval-covered-p iv covering)) shadow))
)
;; ---- Selezione di una singola LWPOLYLINE valida ------------
(defun tc:pick (msg / sel en)
	(while (not en)
		(setq sel (entsel msg))
		(cond
			((null sel) 
				(setq en 'annulla)
			)
			((/= (cdr (assoc 0 (entget (car sel)))) "LWPOLYLINE")
				(princ "\nL'oggetto non e' una LWPOLYLINE.")
			)
			((tc:has-bulge (car sel))
				(princ "\nLa polilinea contiene archi: non supportata.")
			)
			(T 
				(setq en (car sel))
			)
		)
	)
	(if (= en 'annulla) nil en)
)

;; ---- Selezione di piu' LWPOLYLINE valide, INVIO per finire --
(defun tc:pick-many (msg / result sel en stop)
	(setq result nil stop nil)
	(while (not stop)
		(setq sel (entsel (strcat "\n" msg " (INVIO per terminare): ")))
		(cond
			((null sel) 
				(setq stop T)
			)
			(T
				(setq en (car sel))
				(cond
					((/= (cdr (assoc 0 (entget en))) "LWPOLYLINE")
						(princ "\nL'oggetto non e' una LWPOLYLINE, ignorato."))
					((tc:has-bulge en)
						(princ "\nPolilinea con archi, non supportata, ignorata.")
					)
					((member en result)
						(princ "\nGia' selezionato.")
					)
					(T (setq result (cons en result))
						(princ (strcat "\n -> " (itoa (length result)) " selezionato/i."))
					)
				)
			)
		)
	)
	(reverse result)
)
;; ---- Comando principale ------------------------------------
(defun C:TOCCA (/ ea lsb kw ang d p va edges-a data en verts edges dmin
                  shadow results coverage kept item tt best)
	(setq ea (tc:pick "\nSeleziona il poligono da spostare (A): "))
	(if ea
		(progn
			(setq lsb (tc:pick-many "Seleziona i poligoni fissi (B)"))
			(if lsb
				(progn
					(initget "X+ X- Y+ Y- Angolo")
					(setq kw (getkword "\nDirezione [X+/X-/Y+/Y-/Angolo] <X+>: "))
					(if (null kw) (setq kw "X+"))
					(cond
						((= kw "X+") (setq d (list  1.0  0.0)))
						((= kw "X-") (setq d (list -1.0  0.0)))
						((= kw "Y+") (setq d (list  0.0  1.0)))
						((= kw "Y-") (setq d (list  0.0 -1.0)))
						(T
							(setq ang (getangle "\nAngolo di traslazione: "))
							(if ang (setq d (list (cos ang) (sin ang))))
						)
					)
					(if d
						(progn
							;; asse perpendicolare a d (ruotato di 90 gradi)
							(setq p (list (- (cadr d)) (car d)))

							(setq va      (tc:verts ea)
								  edges-a (tc:edges va)
							)
							;; --- dati per ciascun B: verts, edges, dmin, ombra ---
							(setq results nil)
							(foreach en lsb
								(setq verts  (tc:verts en)
									  edges  (tc:edges verts)
									  dmin   (tc:min-projection verts d)
									  shadow (tc:shadow-intervals verts edges d p)
								)
								(setq results (cons (list en verts edges dmin shadow) results))
							)
							(setq results (reverse results))
							;; --- ordina per dmin crescente: il piu' vicino ad A prima,
							;;     lungo la direzione di moto ----------------------
							(setq results
								(vl-sort results '(lambda (x y) (< (nth 3 x) (nth 3 y))))
							)
							;; --- filtro: scarta i B la cui ombra e' interamente
							;;     coperta da quella dei B piu' vicini gia' accettati
							(setq coverage nil kept nil)
							(foreach item results
								(setq shadow (nth 4 item))
								(if (tc:shadow-covered-p shadow coverage)
									(princ	(strcat "\n  - escluso (handle "
											(cdr (assoc 5 (entget (car item)))) "): in ombra.")
									)
									(progn
										(setq kept (cons item kept))
										(if shadow
											(setq coverage (tc:merge-intervals (append coverage shadow)))
										)
									)
								)
							)
							(setq kept (reverse kept))
							(princ	(strcat "\n" (itoa (length lsb)) " poligoni B, "
												 (itoa (length kept)) " da verificare dopo il filtro d'ombra.")
							)
							;; --- calcolo del contatto solo sui B superstiti ------
							(setq best nil)
							(foreach item kept
								(setq tt (tc:distance2 va edges-a (nth 1 item) (nth 2 item) d))
								(if (and tt (or (null best) (< tt (cdr best))))
									(setq best (cons (car item) tt))
								)
							)
							(cond
								((null best)
									(princ "\nNessun contatto possibile in questa direzione.")
								)
								(T
									(setq tt (cdr best))
									(if (> tt 0.0)
										(vla-move
											(vlax-ename->vla-object ea)
											(vlax-3d-point '(0.0 0.0 0.0))
											(vlax-3d-point (list (* tt (car d)) (* tt (cadr d)) 0.0))
										)
									)
									(princ
										(strcat "\nContatto con handle "
												(cdr (assoc 5 (entget (car best))))
												" - traslato di " (rtos tt 2 6) " unita'."
										)
									)
								)
							)
						)
					)
				)
				(princ "\nNessun poligono B selezionato.")
			)
		)
	)
	(princ)
)

(princ "\nComando TOCCA caricato.")
(princ)
